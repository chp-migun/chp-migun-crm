;;; ==================================================================
;;;  MIGUN.LSP — כלי נספחי מיגון ליועץ מיגון
;;;  קובץ זה נוצר מתוך migun.lsp.src על ידי build_lsp.py — אין לערוך ידנית.
;;;
;;;  פקודות:
;;;    MMD      סימון מרחב מוגן בתוכנית האדריכלית (מדידה בקליקים)
;;;    MMDDRAW  יצירת נספח: תוכניות + חתכים + טבלה מרכזת + הערות
;;;    MMDLIST  רשימת המרחבים שנאספו
;;;    MMDDEL   מחיקת מרחב מהרשימה
;;;    MMDCLR   ניקוי הרשימה כולה
;;;    MMDTEST  בדיקה עצמית ללא קליקים — מצייר נספח הדגמה + דוח תקינות
;;;    MMDWIPE  מחיקת כל מה שהכלי צייר
;;;
;;;  הנתונים נשמרים בתוך קובץ ה-DWG (named object dictionary),
;;;  כך שאפשר לסגור ולהמשיך אחר כך.
;;; ==================================================================

(vl-load-com)

;;; ---------- הגדרות ----------
;;; חותמת בנייה — build_lsp.py מחליף את 9bc10ae9 בחתימה של migun.lsp.src.
;;; אותו מקור ? אותה חותמת (אין "רעש" בגיט). אם MMDTEST מדפיס חותמת
;;; שונה מזו שבמקור — אוטוקאד טען קובץ ישן.
(setq *MG-BUILD* "9bc10ae9")
(setq *MG-PREFIX* "MIGUN-")
(setq *MG-FONT*   "arial.ttf")
(setq *MG-UNITS*  1.0)   ; 1.0 = השרטוט בס"מ ; 0.01 = השרטוט במטרים ; 10.0 = מ"מ
(setq *MG-FILL*   7.0)   ; עובי מילוי/ריצוף מעל רצפת הבטון (ס"מ) — ברירת מחדל

;;; שכבות: (שם צבע סוג-קו)
(setq *MG-LAYERS* '(("WALL" 7 "Continuous") ("HATCH" 8 "Continuous")
                    ("DOOR" 3 "Continuous") ("WINDOW" 4 "Continuous")
                    ("VENT" 6 "Continuous") ("DIM" 2 "Continuous")
                    ("TEXT" 7 "Continuous") ("TABLE" 7 "Continuous")
                    ("SECTION" 1 "Continuous") ("HIDDEN" 5 "HIDDEN2")
                    ("MARK" 6 "DASHED2") ("BASE" 8 "Continuous")))

;;; פי כמה מגדילים את הגאומטריה הגזורה מהתוכנית.
;;; **1.0 — הגאומטריה נשארת בגודל אמיתי.** החלטת המשתמש, 27.08.2026:
;;; "רק בהדפסה נעשה את זה בהגדרה בלייאאוט". כלומר קנה המידה 1:50 נקבע
;;; בקנה המידה של הוויופורט בפריסה, לא בהגדלת השרטוט.
;;; יתרון: מידה שנמדדת בשרטוט היא המידה האמיתית, בלי DIMLFAC ובלי
;;; לזכור פי כמה הוכפל מה. הפרמטר נשאר ניתן לשינוי בפקודה למקרה
;;; שבכל זאת יידרש פרט בהגדלה.
(setq *MG-CUTSCALE* 1.0)

;;; גזירות שנעשו בסשן: (שם-בלוק פוליגון-בקואורדינטות-הנספח הגדלה)
(if (null *MG-CUTS*) (setq *MG-CUTS* '()))

;;; ---------- עזרי בסיס ----------
(defun mg:lay (nm / e) (strcat *MG-PREFIX* nm))

(defun mg:mklayers ( / rec nm)
  (foreach rec *MG-LAYERS*
    (setq nm (strcat *MG-PREFIX* (car rec)))
    (if (not (tblsearch "LAYER" nm))
      (entmake (list '(0 . "LAYER") '(100 . "AcDbSymbolTableRecord")
                     '(100 . "AcDbLayerTableRecord")
                     (cons 2 nm) '(70 . 0) (cons 62 (cadr rec))
                     (cons 6 (mg:lt (caddr rec))))))))

(defun mg:lt (nm)
  (if (not (tblsearch "LTYPE" nm))
    (foreach f '("acadiso.lin" "acad.lin")
      (if (not (tblsearch "LTYPE" nm))
        (vl-catch-all-apply 'vl-cmdf (list "_.-LINETYPE" "_Load" nm f "")))))
  (if (tblsearch "LTYPE" nm) nm "Continuous"))

(defun mg:style ( / nm)
  (setq nm (strcat *MG-PREFIX* "TXT"))
  (if (not (tblsearch "STYLE" nm))
    (entmake (list '(0 . "STYLE") '(100 . "AcDbSymbolTableRecord")
                   '(100 . "AcDbTextStyleTableRecord")
                   (cons 2 nm) '(70 . 0) '(40 . 0.0) '(41 . 1.0)
                   '(50 . 0.0) '(71 . 0) '(42 . 2.5)
                   (cons 3 *MG-FONT*) '(4 . ""))))
  nm)

;;; יוצרי ישויות — entmake בלבד
(defun mg:line (ly p1 p2)
  (entmake (list '(0 . "LINE") '(100 . "AcDbEntity") (cons 8 (mg:lay ly))
                 '(100 . "AcDbLine") (cons 10 p1) (cons 11 p2))))

(defun mg:pline (ly pts closed / d)
  (setq d (list '(0 . "LWPOLYLINE") '(100 . "AcDbEntity") (cons 8 (mg:lay ly))
                '(100 . "AcDbPolyline") (cons 90 (length pts))
                (cons 70 (if closed 1 0))))
  (foreach p pts (setq d (append d (list (cons 10 (list (car p) (cadr p)))))))
  (entmake d))

(defun mg:rect (ly x1 y1 x2 y2)
  (mg:pline ly (list (list x1 y1) (list x2 y1) (list x2 y2) (list x1 y2)) T))

(defun mg:circle (ly c r)
  (entmake (list '(0 . "CIRCLE") '(100 . "AcDbEntity") (cons 8 (mg:lay ly))
                 '(100 . "AcDbCircle") (cons 10 c) (cons 40 r))))

(defun mg:arc (ly c r a0 a1)
  (entmake (list '(0 . "ARC") '(100 . "AcDbEntity") (cons 8 (mg:lay ly))
                 '(100 . "AcDbCircle") (cons 10 c) (cons 40 r)
                 '(100 . "AcDbArc") (cons 50 a0) (cons 51 a1))))

;;; טקסט: ha: 0=שמאל 1=מרכז 2=ימין ; va: 0=בסיס 1=תחתית 2=אמצע 3=עליון
(defun mg:text (ly p h s ha va / d)
  (setq d (list '(0 . "TEXT") '(100 . "AcDbEntity") (cons 8 (mg:lay ly))
                '(100 . "AcDbText") (cons 10 p) (cons 40 h) (cons 1 s)
                '(50 . 0.0) (cons 7 (strcat *MG-PREFIX* "TXT"))
                (cons 72 ha) (cons 11 p) '(100 . "AcDbText") (cons 73 va)))
  (entmake d))

;;; hatch אלכסוני 45° בין שני אלכסונים — קווים מפורשים
(defun mg:hatch (ly x1 y1 x2 y2 sp / step c xa xb)
  (if (and (> x2 x1) (> y2 y1))
    (progn
      (setq step (* sp (sqrt 2.0)))
      (setq c (* step (float (fix (/ (- y1 x2) step)))))
      (while (<= c (- y2 x1))
        (setq xa (max x1 (- y1 c)) xb (min x2 (- y2 c)))
        (if (> (- xb xa) 1e-6)
          (mg:line ly (list xa (+ xa c)) (list xb (+ xb c))))
        (setq c (+ c step))))))

(defun mg:hrect (lyr lyh x1 y1 x2 y2 sp hatch?)
  (mg:rect lyr x1 y1 x2 y2)
  (if hatch? (mg:hatch lyh x1 y1 x2 y2 sp)))

;;; מידה ליניארית אמיתית
(defun mg:dim (h? p1 p2 pd)
  (setvar "CLAYER" (mg:lay "DIM"))
  (vl-catch-all-apply 'vl-cmdf
    (list "_.DIMLINEAR" p1 p2 (if h? "_H" "_V") pd)))

;;; וקטורים
(defun v+ (a b) (mapcar '+ a b))
(defun v- (a b) (mapcar '- a b))
(defun v* (a s) (mapcar '(lambda (x) (* x s)) a))
(defun vdot (a b) (apply '+ (mapcar '* a b)))
(defun vlen (a) (sqrt (vdot a a)))
(defun vnorm (a) (v* a (/ 1.0 (max 1e-12 (vlen a)))))
(defun mg:2d (p) (list (car p) (cadr p)))

;;; ---------- שמירה בקובץ ה-DWG ----------
(defun mg:save ()
  (vlax-ldata-put "MIGUN-ANNEX" "spaces" *MMD-LIST*))
(defun mg:load ()
  (setq *MMD-LIST* (cond ((vlax-ldata-get "MIGUN-ANNEX" "spaces")) (nil))))
(mg:load)

;;; ==================================================================
;;;  MMD — איסוף מרחב מוגן מהתוכנית האדריכלית
;;; ==================================================================
;;; מבנה רשומה:
;;; (id L W H (tN tE tS tW) tCeil tFloor
;;;  ((type side off w h sill hinge) ...))
;;;  type: "door" | "win" | "vent" ; side: "N"|"E"|"S"|"W"
;;; ==================================================================

(defun mg:localize (p org u v)
  (list (vdot (v- (mg:2d p) org) u) (vdot (v- (mg:2d p) org) v)))

;;; זיהוי הפאה הקרובה לנקודה מקומית
(defun mg:nearside (lp L W / x y ds best)
  (setq x (car lp) y (cadr lp))
  (setq ds (list (list (abs y) "S") (list (abs (- W y)) "N")
                 (list (abs x) "W") (list (abs (- L x)) "E")))
  (setq best (car ds))
  (foreach d (cdr ds) (if (< (car d) (car best)) (setq best d)))
  (cadr best))

;;; מיקום לאורך הקיר (מרחק מראשית הצלע)
(defun mg:alongwall (lp side)
  (if (or (= side "S") (= side "N")) (car lp) (cadr lp)))

(defun mg:getreal-def (msg def / r)
  (setq r (getreal (strcat "\n" msg " <" (rtos def 2 1) ">: ")))
  (if r r def))

(defun mg:getthick (msg base def / p r)
  ;; מקבל מספר מוקלד או מרחק שנמדד בקליק מנקודת הבסיס
  (setq r (getdist base (strcat "\n" msg " <" (rtos def 2 1) ">: ")))
  (if r r def))

(defun c:MMD ( / *error* osm id p1 p2 p3 org u v d3 L W tmp H
                 tN tE tS tW tC tF fl ops go typ p q lp lq side off
                 opw hgt sill hinge cen dia zc mid rec n dtyp)
  (defun *error* (m)
    (if osm (setvar "OSMODE" osm))
    (if (and m (not (wcmatch (strcase m) "*BREAK*,*CANCEL*,*QUIT*")))
      (princ (strcat "\nMMD: " m)))
    (princ))

  (mg:mklayers) (mg:style)
  (if (null *MMD-LIST*) (mg:load))

  ;; מזהה
  (setq n (1+ (length *MMD-LIST*)))
  (setq id (getstring T (strcat "\nשם המרחב <" "MM-" (itoa n) ">: ")))
  (if (= id "") (setq id (strcat "MM-" (itoa n))))

  ;; שלוש נקורות: פינה, כיוון, פינה נגדית
  (setq osm (getvar "OSMODE"))
  (setvar "OSMODE" 33)  ; endpoint + intersection — כאן דווקא רוצים הצמדה
  (setq p1 (getpoint "\nפינה פנימית ראשונה של המרחב: "))
  (if (null p1) (exit))
  (setq p2 (getpoint p1 "\nנקודה על הפאה הפנימית לאורך (קובעת את כיוון ה-אורך): "))
  (if (null p2) (exit))
  (setq p3 (getpoint p1 "\nהפינה הפנימית הנגדית: "))
  (if (null p3) (exit))

  (setq org (mg:2d p1))
  (setq u (vnorm (v- (mg:2d p2) org)))
  (setq v (list (- (cadr u)) (car u)))           ; ניצב שמאלה
  (setq d3 (mg:localize p3 org u v))
  ;; נירמול: L,W חיוביים — הפיכת צירים במקרה הצורך
  (if (< (car d3) 0) (setq u (v* u -1.0)))
  (setq v (list (- (cadr u)) (car u)))
  (if (< (vdot (v- (mg:2d p3) org) v) 0) (setq v (v* v -1.0)))
  (setq d3 (mg:localize p3 org u v))
  (setq L (car d3) W (cadr d3))
  (princ (strcat "\nנמדד: " (rtos L 2 1) " x " (rtos W 2 1)
                 " (שטח " (rtos (/ (* L W) 10000.0) 2 2) " מ\"ר)"))

  ;; עוביים — קליק על הפאה החיצונית או הקלדה
  (setvar "OSMODE" 512)  ; nearest — לקליק על פאה חיצונית
  (setq mid (v+ org (v+ (v* u (* 0.5 L)) (v* v W))))
  (setq tN (mg:getthick "עובי קיר צפון (הפאה הרחוקה מהפינה הראשונה)" mid 25.0))
  (setq mid (v+ org (v* v (* 0.5 W))))
  (setq tW (mg:getthick "עובי קיר מערב" mid 25.0))
  (setq mid (v+ org (v* u (* 0.5 L))))
  (setq tS (mg:getthick "עובי קיר דרום (קיר הפינה הראשונה)" mid 25.0))
  (setq mid (v+ org (v+ (v* u L) (v* v (* 0.5 W)))))
  (setq tE (mg:getthick "עובי קיר מזרח" mid 25.0))
  (setvar "OSMODE" 0)

  (setq H  (mg:getreal-def "גובה פנים נטו (ס\"מ)" 250.0))
  (setq tC (mg:getreal-def "עובי תקרה" 20.0))
  (setq tF (mg:getreal-def "עובי רצפת בטון" 15.0))
  (setq fl (mg:getreal-def "עובי מילוי/ריצוף מעל הבטון" *MG-FILL*))

  ;; פתחים
  (setq ops '() go T)
  (setvar "OSMODE" 33)
  (while go
    (initget "Delet Halon Tzinor Enter")
    (setq typ (getkword "\nהוסף פתח [דלת(D)/חלון(H)/צינור(T)] או Enter לסיום: "))
    (cond
      ((or (null typ) (= typ "Enter")) (setq go nil))

      ((= typ "Delet")
       (setq p (getpoint "\nמשקוף ראשון על הפאה הפנימית: "))
       (setq q (getpoint p "\nמשקוף שני: "))
       (if (and p q)
         (progn
           (setq lp (mg:localize p org u v) lq (mg:localize q org u v))
           (setq side (mg:nearside lp L W))
           (setq off (min (mg:alongwall lp side) (mg:alongwall lq side)))
           (setq opw (abs (- (mg:alongwall lp side) (mg:alongwall lq side))))
           (setq hgt (mg:getreal-def "גובה הדלת" 200.0))
           (initget "1 2 3 4 5 7 0")
           (princ "\n  סוגי דלת: 1=דירתית 2=דלית-צירית 3=דלית-נגררת")
           (princ "\n            4=ורסיסים-משופרת 5=מוסדית/קומתית 7=רסיסים-25מ\"מ 0=אחר")
           (setq dtyp (cond ((getkword "\nסוג דלת [1/2/3/4/5/7/0] <1>: ")) ("1")))
           (setq hinge (getpoint "\nקליק ליד משקוף הציר: "))
           (setq hinge
             (if hinge
               (if (< (abs (- (mg:alongwall (mg:localize hinge org u v) side) off))
                      (abs (- (mg:alongwall (mg:localize hinge org u v) side) (+ off opw))))
                 "A" "B") "A"))
           (setq ops (cons (list "door" side off opw hgt 0.0 hinge dtyp) ops))
           (mg:check-door opw hgt dtyp)
           (princ (strcat "\nדלת " (rtos opw 2 0) "/" (rtos hgt 2 0)
                          " בקיר " side " במרחק " (rtos off 2 0))))))

      ((= typ "Halon")
       (setq p (getpoint "\nצד ראשון של פתח החלון: "))
       (setq q (getpoint p "\nצד שני: "))
       (if (and p q)
         (progn
           (setq lp (mg:localize p org u v) lq (mg:localize q org u v))
           (setq side (mg:nearside lp L W))
           (setq off (min (mg:alongwall lp side) (mg:alongwall lq side)))
           (setq opw (abs (- (mg:alongwall lp side) (mg:alongwall lq side))))
           (setq hgt (mg:getreal-def "גובה החלון" 100.0))
           (setq sill (mg:getreal-def "גובה אדן מהרצפה" 100.0))
           (setq ops (cons (list "win" side off opw hgt sill "A") ops))
           (princ (strcat "\nחלון " (rtos opw 2 0) "/" (rtos hgt 2 0)
                          " בקיר " side)))))

      ((= typ "Tzinor")
       (setq cen (getpoint "\nמרכז הצינור על הקיר: "))
       (if cen
         (progn
           (setq dia (mg:getreal-def "קוטר (ס\"מ)" 20.0))
           (setq zc (mg:getreal-def "גובה מרכז מהרצפה" 190.0))
           (setq lp (mg:localize cen org u v))
           (setq side (mg:nearside lp L W))
           (setq off (- (mg:alongwall lp side) (/ dia 2.0)))
           (setq ops (cons (list "vent" side off dia dia zc "A") ops))
           (mg:check-vent side off dia zc ops L W)
           (princ (strcat "\nצינור " (rtos dia 2 0) " בקיר " side)))))))
  (setvar "OSMODE" osm)

  ;; סימון על גבי התוכנית — שכבת MARK
  (mg:mark org u v L W id)

  ;; fl נוסף בסוף בכוונה — רשומות שנשמרו לפני שהשדה קיים עדיין נטענות.
  (setq rec (list id L W H (list tN tE tS tW) tC tF (reverse ops) fl))
  (setq *MMD-LIST* (append *MMD-LIST* (list rec)))
  (mg:save)
  (princ (strcat "\n=== " id " נוסף. סה\"כ " (itoa (length *MMD-LIST*))
                 " מרחבים. MMDDRAW ליצירת הנספח. ==="))
  (princ))

;;; מסגרת סימון על התוכנית האדריכלית
(defun mg:mark (org u v L W id / c)
  (mg:pline "MARK"
    (list org (v+ org (v* u L)) (v+ org (v+ (v* u L) (v* v W))) (v+ org (v* v W))) T)
  (setq c (v+ org (v+ (v* u (* 0.5 L)) (v* v (* 0.5 W)))))
  (mg:text "MARK" c (* 0.12 (min L W)) id 1 2))

;;; ==================================================================
;;;  בדיקות רכות — התראות בלבד, לעולם לא חוסמות
;;;  מקורות: תשובות המשתמש 26.08.2026; הנחיית ענף הנדסה 10.06.2019;
;;;  טבלת דלתות ת"י 4422
;;; ==================================================================

(defun mg:warn (msg) (princ (strcat "\n  !! " msg)))

(defun mg:check-door (w hgt dtyp)
  ;; רוחבים תקניים לפי סוג הדלת
  (cond
    ((member dtyp '("1" "2" "3" "4"))
     (if (not (member (fix (+ w 0.5)) '(70 80)))
       (mg:warn (strcat "רוחב דלת דירתית " (rtos w 2 0)
                        " — התקניים הם 70/80 ס\"מ"))))
    ((= dtyp "5")
     (if (not (member (fix (+ w 0.5)) '(85 90 100)))
       (mg:warn (strcat "רוחב דלת מוסדית/קומתית " (rtos w 2 0)
                        " — התקניים הם 85/90/100 ס\"מ"))))
    ((= dtyp "7")
     (if (or (< w 70) (> w 100))
       (mg:warn "דלת רסיסים 25 מ\"מ: רוחב 70-100 ס\"מ"))))
  (if (< hgt 200)
    (mg:warn (strcat "גובה דלת " (rtos hgt 2 0) " — מתחת ל-200 ס\"מ"))))

;;; בדיקת צינור לפי טבלת ההנחיה 2019 (ממ"ד): כניסה MIN 150 מהרצפה,
;;; יציאה MIN 190; מרחק מקיר ניצב 25-40 MIN; אסור מעל דלת/חלון;
;;; 60 ס"מ בין צינורות; 25-45 ס"מ מדופן פתח
(defun mg:check-vent (side off dia zc ops L W / span gap o mind)
  (setq span (if (or (= side "S") (= side "N")) L W))
  (setq gap (min off (- span off dia)))
  (if (< gap 25)
    (mg:warn (strcat "צינור במרחק " (rtos gap 2 0)
                     " ס\"מ מקיר ניצב — טבלת ההנחיה דורשת 25-40 לפחות")))
  (if (< zc 150)
    (mg:warn (strcat "מרכז הצינור בגובה " (rtos zc 2 0)
                     " — כניסת אוויר מינימום 150, יציאה 190")))
  ;; מרחק מפתחים אחרים על אותו קיר + איסור מעל פתח
  (foreach o (cdr ops)   ; ops כולל את הצינור עצמו בראש
    (if (= (cadr o) side)
      (progn
        (setq mind (if (= (car o) "vent") 60 25))
        (setq gap (cond ((> off (+ (caddr o) (cadddr o))) (- off (caddr o) (cadddr o)))
                        ((> (caddr o) (+ off dia)) (- (caddr o) off dia))
                        (T -1)))
        (cond
          ((< gap 0)
           (if (/= (car o) "vent")
             (mg:warn (strcat "הצינור מעל/בתוך פתח " (car o)
                              " — אסור מעל דלת או חלון"))))
          ((< gap mind)
           (mg:warn (strcat "מרחק " (rtos gap 2 0) " ס\"מ מ-" (car o)
                            " — נדרש " (itoa mind) " לפחות"))))))))

;;; ==================================================================
;;;  MMDLIB — טעינת ספריית הבלוקים (migun-lib.dwg ליד קובץ ה-LISP)
;;; ==================================================================
(defun mg:libpath ( / base)
  (setq base (findfile "migun-lib.dwg"))
  (if (null base)
    (setq base (findfile (strcat (vl-filename-directory
      (cond ((findfile "migun.lsp")) (""))) "\\migun-lib.dwg"))))
  base)

(defun c:MMDLIB ( / p e0)
  (setq p (mg:libpath))
  (cond
    ((null p)
     (princ "\nלא נמצא migun-lib.dwg. פתח את migun-lib.dxf באוטוקאד ושמור אותו")
     (princ "\nכ-migun-lib.dwg באותה תיקייה שבה נמצא migun.lsp."))
    ((tblsearch "BLOCK" "Prat petach chalon")
     (princ "\nספריית הבלוקים כבר טעונה בשרטוט."))
    (T
     (setq e0 (entlast))
     (vl-catch-all-apply 'vl-cmdf (list "_.-INSERT" p '(0 0 0) 1 1 0))
     ;; מחיקת ההוספה עצמה — ההגדרות המקוננות נשארות בטבלת הבלוקים
     (if (not (eq e0 (entlast))) (entdel (entlast)))
     (princ "\nהספרייה נטענה — הבלוקים זמינים כעת בשרטוט.")))
  (princ))

;;; ==================================================================
;;;  MMDDETAILS — הוספת פרטי פתחים לכל מרחב שנאסף
;;;  משתמש בבלוקים של המשרד: "Prat petach chalon" / "Prat petach bdelet"
;;; ==================================================================
(defun mg:insblock (nm pt scl / )
  (if (tblsearch "BLOCK" nm)
    (progn
      (entmake (list '(0 . "INSERT") '(100 . "AcDbEntity")
                     (cons 8 (mg:lay "TABLE"))
                     '(100 . "AcDbBlockReference")
                     (cons 2 nm) (cons 10 pt)
                     (cons 41 scl) (cons 42 scl) (cons 43 scl)))
      T)
    (progn (mg:warn (strcat "הבלוק \"" nm "\" אינו בשרטוט — הרץ MMDLIB")) nil)))

(defun c:MMDDETAILS ( / p0 x y r o names gap scl)
  (if (null *MMD-LIST*) (mg:load))
  (if (null *MMD-LIST*)
    (progn (princ "\nאין מרחבים — הרץ MMD קודם.") (exit)))
  (setq p0 (getpoint "\nנקודת בסיס לשורת הפרטים: "))
  (if (null p0) (exit))
  (setq scl (getreal "\nקנה מידה להוספת הפרטים <1.0>: "))
  (if (null scl) (setq scl 1.0))
  (setq x (car p0) y (cadr p0) gap 550.0)
  (foreach r *MMD-LIST*
    (foreach o (nth 7 r)
      (cond
        ((= (car o) "win")
         (if (mg:insblock "Prat petach chalon" (list x y 0.0) scl)
           (setq x (- x (* gap scl)))))
        ((= (car o) "door")
         (if (mg:insblock "Prat petach bdelet" (list x y 0.0) scl)
           (setq x (- x (* gap scl))))))))
  (princ "\nהפרטים הוזרקו. ערוך מידות וזיון לפי הפרויקט.")
  (princ))

;;; ==================================================================
;;;  MMDDRAW — יצירת הנספח
;;; ==================================================================

;;; ==================================================================
;;;  פוליגון — מרחב מוגן שאינו מלבני
;;;  המשתמש (27.08.2026): "יש מלא ממ"דים שהם לא מלבנים".
;;;  כל הציור עובד מעכשיו על פוליגון. מלבן הוא פשוט פוליגון בן 4 צלעות
;;;  שנבנה מ-L/W/עוביים, כך שיש **מסלול קוד אחד בלבד** ורשומות ישנות
;;;  ממשיכות לעבוד בלי המרה.
;;; ==================================================================

;;; ---------- קריאת הגאומטריה של האדריכל ----------
;;; המשתמש (27.08.2026): "למה אני צריך לסמן את הקירות — תגזור את מה
;;; שיש ותביא אותו לנספח". לכן: קליק אחד בתוך החדר, ואוטוקאד עצמו
;;; מתחקה את קו הפנים דרך ‎-BOUNDARY. זה תופס נישות, כיסים וכל צורה
;;; שהיא — בלי הנחת מלבן ובלי שהמשתמש יתווה שום דבר.

;;; קודקודי LWPOLYLINE
(defun mg:plpts (e / d pts)
  (setq d (entget e) pts '())
  (foreach x d (if (= (car x) 10) (setq pts (cons (mg:2d (cdr x)) pts))))
  (reverse pts))

;;; ניסיון תיחקות בודד בסובלנות פערים נתונה
(defun mg:btry (pt tol / e0 e pts gt)
  (setq e0 (entlast) gt (getvar "HPGAPTOL"))
  (vl-catch-all-apply 'setvar (list "HPGAPTOL" tol))
  (vl-catch-all-apply 'vl-cmdf (list "_.-BOUNDARY" pt ""))
  (vl-catch-all-apply 'setvar (list "HPGAPTOL" gt))
  (setq e (entlast))
  (if (and e (not (eq e e0)) (= (cdr (assoc 0 (entget e))) "LWPOLYLINE"))
    (progn (setq pts (mg:plpts e)) (entdel e) pts)
    nil))

;;; קו פנים של החדר שבו נמצאת הנקודה, בקואורדינטות עולם.
;;; מנסה סובלנות פערים הולכת וגדלה: קווי אדריכל לא תמיד נפגשים,
;;; ובעיקר — פתח דלת משאיר פרצה של 80–100 ס"מ שסוגרת את הדרך.
;;; אחרי כל ניסיון נבדקת סבירות: מרחב מוגן אינו גדול מ-20 מ' לצלע
;;; ואינו קטן מ-1 מ'. תוצאה לא סבירה נדחית — עדיף כישלון גלוי
;;; מאשר לתחקות בטעות את כל הדירה ולדווח עליה כעל ממ"ד.
(defun mg:bpoly (pt / tols pts bb w h res used)
  (setq tols '(5.0 30.0 70.0 110.0 160.0) res nil)
  (foreach tol tols
    (if (null res)
      (progn
        (setq pts (mg:btry pt tol))
        (if (and pts (> (length pts) 2))
          (progn
            (setq bb (mg:bbox pts))
            (setq w (- (caddr bb) (car bb)) h (- (cadddr bb) (cadr bb)))
            (if (and (> w 100.0) (> h 100.0) (< w 2000.0) (< h 2000.0))
              (setq res pts used tol)
              (princ (strcat "\n  (סובלנות " (rtos tol 2 0) ": התקבל "
                             (rtos w 2 0) "x" (rtos h 2 0)
                             " — לא סביר, ממשיך)"))))))))
  (if res (princ (strcat "\n  קו פנים נסגר בסובלנות פערים "
                         (rtos used 2 0) " ס\"מ")))
  res)

;;; זריקת קרן מנקודה בכיוון dir; מחזירה את המרחק למכשול הקרוב ביותר
;;; מבין הישויות ב-ss, או nil. כך נמדד עובי הקיר בלי לשאול את המשתמש.
(defun mg:ray (p dir maxd ss / q i e d segs s best x t1)
  (setq q (list (+ (car p) (* (car dir) maxd)) (+ (cadr p) (* (cadr dir) maxd))))
  (setq best nil i 0)
  (if ss
    (repeat (sslength ss)
      (setq e (ssname ss i) i (1+ i))
      (setq d (entget e))
      (setq segs
        (cond ((= (cdr (assoc 0 d)) "LINE")
               (list (list (mg:2d (cdr (assoc 10 d))) (mg:2d (cdr (assoc 11 d))))))
              ((= (cdr (assoc 0 d)) "LWPOLYLINE")
               (mg:pairs (mg:plpts e) (= 1 (logand 1 (cdr (assoc 70 d))))))
              (T nil)))
      (foreach s segs
        (setq x (inters p q (car s) (cadr s) T))
        (if x
          (progn (setq t1 (distance p x))
                 (if (and (> t1 0.5) (or (null best) (< t1 best)))
                   (setq best t1)))))))
  best)

;;; רשימת נקודות ? רשימת קטעים
(defun mg:pairs (pts closed / n i out)
  (setq n (length pts) i 0 out '())
  (while (< i (1- n))
    (setq out (cons (list (nth i pts) (nth (1+ i) pts)) out))
    (setq i (1+ i)))
  (if (and closed (> n 2))
    (setq out (cons (list (nth (1- n) pts) (car pts)) out)))
  (reverse out))

;;; עובי כל צלע, נמדד מהשרטוט: מאמצע הצלע יוצאת קרן החוצה עד לקו הבא.
;;; מה שלא נמדד מקבל את ברירת המחדל.
(defun mg:measure-th (wpts def / n i p q mid dir nrm ss bb th d)
  (setq n (length wpts) i 0 th '())
  (while (< i n)
    (setq p (nth i wpts) q (nth (rem (1+ i) n) wpts))
    (setq mid (list (/ (+ (car p) (car q)) 2.0) (/ (+ (cadr p) (cadr q)) 2.0)))
    (setq dir (vnorm (list (- (car q) (car p)) (- (cadr q) (cadr p)))))
    (setq nrm (list (cadr dir) (- (car dir))))          ; ימינה = החוצה
    (setq ss (ssget "_C"
                    (list (- (car mid) 90.0) (- (cadr mid) 90.0))
                    (list (+ (car mid) 90.0) (+ (cadr mid) 90.0))
                    '((0 . "LINE,LWPOLYLINE"))))
    (setq d (mg:ray mid nrm 80.0 ss))
    (setq th (cons (if d (mg:round5 d) def) th))
    (setq i (1+ i)))
  (reverse th))

;;; עיגול לחצי-סנטימטר הקרוב — קווי אדריכל אף פעם לא בדיוק על 25.000
(defun mg:round5 (x) (/ (float (fix (+ (* x 2.0) 0.5))) 2.0))

;;; ==================================================================
;;;  גזירת אזור מהתוכנית אל הנספח
;;;
;;;  המשתמש (27.08.2026): "למה שלא יבקש ממני לתחום מסביב לממ"ד".
;;;  שני קליקים במקום ניחוש — וזה גם היחיד שעובד כאן, כי כל תוכנית
;;;  קומה בקובץ הזה היא **בלוק אחד**: תחימה רגילה גוררת את כל הקומה,
;;;  ומחיקת מה שבחוץ לא אפשרית בתוך בלוק.
;;;
;;;  לכן: מעתיקים את מה שנוגע בחלון, כולסים לבלוק חדש, מכניסים אותו
;;;  בהגדלה, וגוזרים ב-XCLIP למלבן שנתחם. XCLIP חותך גם תוכן מקונן,
;;;  כך שלא נשארות זנבות בולטות ואין צורך ב-TRIM.
;;; ==================================================================

;;; שם בלוק פנוי לגזירה הבאה
(defun mg:cutname ( / i nm)
  (setq i 1)
  (while (tblsearch "BLOCK" (setq nm (strcat *MG-PREFIX* "CUT-" (itoa i))))
    (setq i (1+ i)))
  nm)

;;; נקודה מהתוכנית אל מערכת הנספח: יעד + (p - בסיס) * הגדלה
(defun mg:xf (p base target scl)
  (list (+ (car target)  (* (- (car p)  (car base))  scl))
        (+ (cadr target) (* (- (cadr p) (cadr base)) scl))))

;;; הערה על בחירה — נמדד, לא משוער:
;;; ניסיתי לבחור לפי תיבות חוסמות (‎vla-GetBoundingBox על כל ישות),
;;; כדי לא להיות תלויים במה שמוצג על המסך. בקובץ הזה זה לקח **מעל
;;; תשע דקות CPU**: כל תוכנית קומה היא בלוק עם ~3,000 ישויות ובתוכן
;;; בלוקים מקוננים בני 1,900, וחישוב extents רקורסיבי עליהם יקר מאוד.
;;; לכן חוזרים ל-ssget בחלון — מיידי, ותקף כאן כי המשתמש בדיוק תחם
;;; את החלון על המסך, כלומר האזור ודאי מוצג.

;;; גזירת החלון p1..p2 אל target בהגדלה scl. מחזירה את הבלוק שנוצר.
;;; ss אופציונלי — כשהוא nil הבחירה נעשית כאן ב-ssget. הפרמטר קיים
;;; כדי שבדיקה headless תוכל להזריק בחירה (ssget בחלון דורש תצוגה).
(defun mg:cutwin (p1 p2 target scl ss / e0 e nss n nm base np1 np2 res)
  (setq base (list (/ (+ (car p1) (car p2)) 2.0)
                   (/ (+ (cadr p1) (cadr p2)) 2.0)))
  (if (null ss) (setq ss (ssget "_C" p1 p2)))
  (if (null ss)
    (progn
      (mg:warn "לא נמצאה גאומטריה בחלון שתחמת")
      (princ "\n   ודא שכל האזור שתחמת מוצג על המסך — בחירה בחלון")
      (princ "\n   פועלת רק על מה שנראה בתצוגה.")
      nil)
    (progn
      (princ (strcat "\nנבחרו " (itoa (sslength ss)) " ישויות בחלון."))
      (setq e0 (entlast))
      ;; ה-"" האחרון סוגר את COPY: הפקודה חוזרת על עצמה ומבקשת עוד
      ;; עותקים, ובלי הסגירה היא נשארת פתוחה ושום דבר אחריה לא רץ.
      (vl-catch-all-apply 'vl-cmdf (list "_.COPY" ss "" base target ""))
      ;; העותקים = כל מה שנוסף אחרי e0
      (setq nss (ssadd) n 0)
      (setq e (if e0 (entnext e0) (entnext)))
      (while e (ssadd e nss) (setq n (1+ n)) (setq e (entnext e)))
      (if (= n 0)
        (progn (mg:warn "ההעתקה לא יצרה ישויות") nil)
        (progn
          (setq nm (mg:cutname))
          ;; ‎-BLOCK מוחק את הנבחרים — אלה עותקים, המקור לא נגע
          (vl-catch-all-apply 'vl-cmdf (list "_.-BLOCK" nm target nss ""))
          (vl-catch-all-apply 'vl-cmdf
            (list "_.-INSERT" nm target (rtos scl 2 6) (rtos scl 2 6) "0"))
          (setq res (entlast))
          ;; גזירה למלבן שנתחם, מומר למיקום ולהגדלה החדשים
          (setq np1 (mg:xf p1 base target scl)
                np2 (mg:xf p2 base target scl))
          (vl-catch-all-apply 'vl-cmdf
            (list "_.XCLIP" res "" "_New" "_Rectangular" np1 np2))
          (princ (strcat "\nנגזר " nm " — " (itoa n)
                         " ישויות, הגדלה x" (rtos scl 2 2) "."))
          res)))))

;;; ==================================================================
;;;  MMDDIM — מידות, שטח ונפח מעל גזירה קיימת
;;;  לוחצים פעם אחת בתוך המרחב, אוטוקאד מתחקה את קו הפנים, והכלי
;;;  מודד ומסמן. הכל נמדד על הגזירה המוגדלת ומוצג בערכים אמיתיים:
;;;  DIMLFAC = 1/הגדלה למידות, ושטח/נפח מחולקים בריבוע ההגדלה.
;;; ==================================================================
(defun mg:dimpoly (pts scl id H th / n i p q mid dir nrm ins ctr bb
                   a v inw d1 lab)
  (setq n (length pts))
  (setq bb (mg:bbox pts))
  (setq ctr (list (/ (+ (car bb) (caddr bb)) 2.0)
                  (/ (+ (cadr bb) (cadddr bb)) 2.0)))
  (setq d1 (* 0.10 (min (- (caddr bb) (car bb)) (- (cadddr bb) (cadr bb)))))
  ;; מידת פנים לכל צלע, קו המידה בתוך החדר
  (setq i 0)
  (while (< i n)
    (setq p (nth i pts) q (nth (rem (1+ i) n) pts))
    (setq mid (list (/ (+ (car p) (car q)) 2.0) (/ (+ (cadr p) (cadr q)) 2.0)))
    (setq dir (vnorm (list (- (car q) (car p)) (- (cadr q) (cadr p)))))
    (setq nrm (list (- (cadr dir)) (car dir)))       ; שמאלה = פנימה ב-CCW
    (setq ins (list (+ (car mid) (* (car nrm) d1)) (+ (cadr mid) (* (cadr nrm) d1))))
    (mg:dimal p q ins)
    ;; מידת עובי הקיר, אם נמדדה
    (if (and th (nth i th) (> (nth i th) 0.0))
      (progn
        (setq v (list (- (car nrm)) (- (cadr nrm))))
        (mg:dimal mid
                  (list (+ (car mid) (* (car v) (nth i th)))
                        (+ (cadr mid) (* (cadr v) (nth i th))))
                  (list (+ (car mid) (* (car v) (* 0.5 (nth i th))))
                        (+ (cadr mid) (* (cadr v) (* 0.5 (nth i th))))))))
    (setq i (1+ i)))
  ;; שם, שטח ונפח — בערכים אמיתיים
  (setq a (/ (abs (mg:sarea pts)) (* 10000.0 scl scl)))
  (setq lab (* 0.035 (min (- (caddr bb) (car bb)) (- (cadddr bb) (cadr bb)))))
  (mg:text "TEXT" (list (car ctr) (+ (cadr ctr) (* lab 1.9))) (* lab 1.5) id 1 0)
  (mg:text "TEXT" (list (car ctr) (+ (cadr ctr) (* lab 0.1))) lab
           (strcat (rtos a 2 2) " \U+05DE\"\U+05E8") 1 0)
  (if (and H (> H 0.0))
    (mg:text "TEXT" (list (car ctr) (- (cadr ctr) (* lab 1.6))) lab
             (strcat (rtos (* a (/ H 100.0)) 2 2) " \U+05DE\"\U+05E7") 1 0))
  a)

(defun c:MMDDIM ( / *error* sv vals pt wpts scl id H obj ss i e n
                    th p q mid dir nrm d a bb)
  (setq sv (mg:sysvars) vals (mapcar 'getvar sv))
  (defun *error* (m)
    (mapcar '(lambda (x y) (vl-catch-all-apply 'setvar (list x y))) sv vals)
    (if (and m (not (wcmatch (strcase m) "*BREAK*,*CANCEL*,*QUIT*")))
      (princ (strcat "\nMMDDIM: " m)))
    (princ))

  (if (/= (getvar "TILEMODE") 1)
    (progn (princ "\n!! עבור ללשונית Model.") (exit)))
  (mg:mklayers) (mg:style)
  (setvar "CMDECHO" 0)

  ;; שלושה מקורות לקו הפנים, לפי סדר אמינות יורד:
  ;;   1. מה ש-MMDCUT כבר תיחקה בתוכנית המקורית ושמר
  ;;   2. תיחקות ישירה כאן (עובדת רק אם אין בלוק גזור)
  ;;   3. סימון הפינות ידנית
  (setq scl *MG-CUTSCALE* wpts nil)
  (if *MG-CUTS*
    (progn
      (princ (strcat "\nיש " (itoa (length *MG-CUTS*))
                     " גזירות שמורות מהסשן."))
      (setq pt (getpoint "\nלחץ בתוך המרחב שבגזירה (Enter = הגזירה האחרונה): "))
      (if pt
        (progn
          (setq pt (mg:2d pt))
          (foreach c *MG-CUTS*
            (if (and (null wpts) (mg:inpoly pt (cadr c)))
              (setq wpts (cadr c) scl (caddr c)))))
        (progn (setq wpts (cadr (car *MG-CUTS*)) scl (caddr (car *MG-CUTS*)))))
      (if wpts (princ (strcat "\n  נמצא קו שמור: " (itoa (length wpts))
                              " צלעות")))))

  (if (null wpts)
    (progn
      (setq pt (getpoint "\nלחץ בתוך המרחב המוגן: "))
      (if (null pt) (exit))
      (setq pt (mg:2d pt))
      (princ "\nמתחקה את קו הפנים...")
      (setq wpts (mg:bpoly pt))
      (if wpts
        (progn
          (setq scl (mg:getreal-def "הגדלה של הגזירה" *MG-CUTSCALE*))
          (setq wpts (mg:simplify wpts (* 15.0 scl) (/ (* 4.0 pi) 180.0)))
          (setq wpts (car (mg:ccw wpts nil)))
          (princ (strcat "\n  אחרי ניקוי: " (itoa (length wpts)) " צלעות")))
        (progn
          (princ "\n!! לא נסגר קו פנים אוטומטית.")
          (princ "\n   קורה כשהגזירה היא בלוק גזור (XCLIP) — ‎BOUNDARY")
          (princ "\n   לא מתחקה לתוכו — או כשפתח דלת משאיר פרצה גדולה.")
          (princ "\n   סמן את פינות הפנים בקליקים, Enter לסיום:")
          (setq wpts (mg:pickpoly))
          (if (and wpts (> (length wpts) 2))
            (setq wpts (car (mg:ccw wpts nil)))
            (progn (princ "\n!! פחות משלוש פינות.") (exit)))))))

  (if (< (length wpts) 3)
    (progn (princ "\n!! לא נשארו מספיק צלעות.") (exit)))

  (setq bb (mg:bbox wpts))
  (princ (strcat "\n  תיבה חוסמת: " (rtos (/ (- (caddr bb) (car bb)) scl) 2 1)
                 " x " (rtos (/ (- (cadddr bb) (cadr bb)) scl) 2 1) " ס\"מ"))
  (princ (strcat "\n  שטח נטו   : "
                 (rtos (/ (abs (mg:sarea wpts)) (* 10000.0 scl scl)) 2 2) " מ\"ר"))

  ;; עוביי קירות — קרן מול בלוק הגזירה, שרואה גם לתוך בלוקים
  (setq th nil)
  (setq ss (ssget "_X" (list '(0 . "INSERT") (cons 2 (strcat *MG-PREFIX* "CUT*")))))
  (if ss
    (progn
      (princ "\nמודד עוביי קירות...")
      (setq obj (vlax-ename->vla-object (ssname ss 0)))
      (setq n (length wpts) i 0 th '())
      (while (< i n)
        (setq p (nth i wpts) q (nth (rem (1+ i) n) wpts))
        (setq mid (list (/ (+ (car p) (car q)) 2.0) (/ (+ (cadr p) (cadr q)) 2.0)))
        (setq dir (vnorm (list (- (car q) (car p)) (- (cadr q) (cadr p)))))
        (setq nrm (list (cadr dir) (- (car dir))))          ; החוצה
        (setq d (mg:raycast mid nrm (* 80.0 scl) obj))
        (setq th (cons (if d d 0.0) th))
        (setq i (1+ i)))
      (setq th (reverse th))
      (setq i 0 a "")
      (foreach x th
        (setq a (strcat a (if (= i 0) "" " / ")
                        (if (> x 0.0) (rtos (/ x scl) 2 1) "?")))
        (setq i (1+ i)))
      (princ (strcat "\n  עוביים לפי צלע: " a))))

  (setq id (getstring T "\nשם המרחב <ממ\"ד>: "))
  (if (= id "") (setq id "\U+05DE\U+05DE\"\U+05D3"))
  (setq H (mg:getreal-def "גובה פנים נטו (ס\"מ)" 250.0))

  ;; המידות מוצגות בערך אמיתי למרות שהגאומטריה מוגדלת
  (mg:setup 50.0)
  (setvar "DIMLFAC" (/ 1.0 scl))
  (mg:dimpoly wpts scl id H th)

  (mapcar '(lambda (x y) (vl-catch-all-apply 'setvar (list x y))) sv vals)
  (princ "\n=== מידות, שטח ונפח נוספו לגזירה. ===")
  (princ))

;;; ---------- ניקוי קו פנים שהתקבל מ-BOUNDARY ----------
;;; קווי אדריכל מלאים בקפיצות של סנטימטר: מזוזות, טיח, פינות שבורות.
;;; בלי ניקוי מתקבל פוליגון בן עשרות צלעות ולכל אחת מהן מידה — בלתי
;;; קריא לחלוטין. שתי מחיקות: קטע קצר מדי, וקודקוד שכמעט על קו ישר.
(defun mg:simplify (pts mind angtol / n i p q r out changed a1 a2 da ctr sx sy)
  (setq changed T)
  (while changed
    (setq changed nil n (length pts))
    ;; מרכז מסה משוער — משמש להכרעה איזה קודקוד לשמור
    (setq sx 0.0 sy 0.0)
    (foreach p pts (setq sx (+ sx (car p)) sy (+ sy (cadr p))))
    (setq ctr (list (/ sx n) (/ sy n)))
    ;; קטעים קצרים: מוחקים קודקוד אחד מהשניים.
    ;; **שומרים את הקרוב למרכז** — כלומר במקרה של ספק המרחב יוצא
    ;; קטן במעט ולא גדול במעט. בכלי מיגון זה הכיוון הבטוח: עדיף
    ;; לדווח שטח מוגן חסר מאשר עודף מול הרשות המוסמכת.
    (setq out '() i 0)
    (while (< i n)
      (setq p (nth i pts) q (nth (rem (1+ i) n) pts))
      (if (< (distance p q) mind)
        (progn
          (setq changed T)
          (if (< (distance p ctr) (distance q ctr))
            (setq out (cons p out))))         ; p קרוב יותר — הוא שנשאר
        (setq out (cons p out)))
      (setq i (1+ i)))
    (setq pts (reverse out) n (length pts))
    (if (< n 3) (setq changed nil))
    ;; קודקודים כמעט-ישרים
    (if (>= n 3)
      (progn
        (setq out '() i 0)
        (while (< i n)
          (setq p (nth (rem (+ i (1- n)) n) pts)
                q (nth i pts)
                r (nth (rem (1+ i) n) pts))
          (setq a1 (atan (- (cadr q) (cadr p)) (- (car q) (car p))))
          (setq a2 (atan (- (cadr r) (cadr q)) (- (car r) (car q))))
          (setq da (abs (- a2 a1)))
          (if (> da pi) (setq da (- (* 2 pi) da)))
          (if (< da angtol)
            (setq changed T)
            (setq out (cons q out)))
          (setq i (1+ i)))
        (setq pts (reverse out)))))
  pts)

;;; האם נקודה בתוך פוליגון — ray casting, לזיהוי לאיזו גזירה לחצת
(defun mg:inpoly (pt pts / n i p q c x)
  (setq n (length pts) i 0 c nil)
  (while (< i n)
    (setq p (nth i pts) q (nth (rem (1+ i) n) pts))
    (if (and (/= (> (cadr p) (cadr pt)) (> (cadr q) (cadr pt)))
             (< (car pt)
                (+ (car p) (* (- (car q) (car p))
                              (/ (- (cadr pt) (cadr p))
                                 (- (cadr q) (cadr p)))))))
      (setq c (not c)))
    (setq i (1+ i)))
  c)

;;; סימון פינות ידני — מוצא אחרון כשהתיחקות לא מצליחה
(defun mg:pickpoly ( / pts p n osm)
  (setq pts '() n 1 osm (getvar "OSMODE"))
  (setvar "OSMODE" 33)                     ; הצמדה לפינות ולחיתוכים
  (while (setq p (getpoint (strcat "\n  פינה " (itoa n) " (Enter לסיום): ")))
    (setq pts (cons (mg:2d p) pts) n (1+ n)))
  (setvar "OSMODE" osm)
  (reverse pts))

;;; מידה משוכה — עובדת גם על צלע נטויה, לא רק אופקית/אנכית
(defun mg:dimal (p1 p2 pd)
  (setvar "CLAYER" (mg:lay "DIM"))
  (vl-catch-all-apply 'vl-cmdf (list "_.DIMALIGNED" p1 p2 pd)))

;;; זריקת קרן מול ישות אחת (בדרך כלל בלוק הגזירה) — IntersectWith
;;; רואה גם תוכן מקונן, בניגוד ל-ssget. מחזירה מרחק או nil.
(defun mg:raycast (p dir maxd obj / q e r lst i best d x)
  (setq q (list (+ (car p) (* (car dir) maxd)) (+ (cadr p) (* (cadr dir) maxd))))
  (entmake (list '(0 . "LINE") '(100 . "AcDbEntity") (cons 8 "0")
                 '(100 . "AcDbLine")
                 (cons 10 (list (car p) (cadr p) 0.0))
                 (cons 11 (list (car q) (cadr q) 0.0))))
  (setq e (entlast))
  (setq r (vl-catch-all-apply 'vlax-invoke
            (list (vlax-ename->vla-object e) 'IntersectWith obj 0)))
  (entdel e)
  (if (or (vl-catch-all-error-p r) (null r))
    nil
    (progn
      (setq lst r best nil)
      (while (>= (length lst) 3)
        (setq x (list (car lst) (cadr lst)))
        (setq d (distance p x))
        (if (and (> d 0.5) (or (null best) (< d best))) (setq best d))
        (setq lst (cdddr lst)))
      best)))

;;; ==================================================================
;;;  MMDCUT — תחום מסביב לממ"ד, והכלי גוזר אותו אל הנספח
;;; ==================================================================
(defun c:MMDCUT ( / *error* sv vals p1 p2 target scl osm res
                    ipt wpts bb base apts)
  (setq sv (mg:sysvars) vals (mapcar 'getvar sv))
  (defun *error* (m)
    (mapcar '(lambda (a b) (vl-catch-all-apply 'setvar (list a b))) sv vals)
    (if (and m (not (wcmatch (strcase m) "*BREAK*,*CANCEL*,*QUIT*")))
      (princ (strcat "\nMMDCUT: " m)))
    (princ))

  ;; חייבים להיות במרחב המודל. אם פעיל Layout, COPY פשוט לא מעתיק —
  ;; בלי הודעת שגיאה, וקשה מאוד להבין למה כלום לא קורה. נבדק לפני
  ;; הקליקים, כדי שלא לבזבז את התיחום.
  (if (/= (getvar "TILEMODE") 1)
    (progn
      (princ (strcat "\n!! אתה נמצא בפריסה \"" (getvar "CTAB") "\" ולא במודל."))
      (princ "\n   עבור ללשונית Model ונסה שוב — העתקה בין המרחבים")
      (princ "\n   לא מתבצעת, והפקודה הייתה נראית כאילו לא עשתה כלום.")
      (exit)))

  (mg:mklayers) (mg:style)
  (setvar "CMDECHO" 0)
  (setq osm (getvar "OSMODE"))
  (setvar "OSMODE" 0)          ; תוחמים באוויר, בלי שההצמדה תקפיץ פינות

  (princ "\nתחום מלבן סביב המרחב המוגן — קח מרווח, אפשר לגזור שוב.")
  (setq p1 (getpoint "\n  פינה ראשונה: "))
  (if (null p1) (progn (setvar "OSMODE" osm) (exit)))
  (setq p2 (getcorner p1 "\n  פינה נגדית: "))
  (if (null p2) (progn (setvar "OSMODE" osm) (exit)))
  (setq p1 (mg:2d p1) p2 (mg:2d p2))
  (princ (strcat "\nהחלון: " (rtos (abs (- (car p2) (car p1))) 2 1) " x "
                 (rtos (abs (- (cadr p2) (cadr p1))) 2 1) " ס\"מ"))

  (setq scl (mg:getreal-def "הגדלה לנספח" *MG-CUTSCALE*))
  (setq target (getpoint "\nאיפה למקם את הגזירה בנספח: "))
  (if (null target) (progn (setvar "OSMODE" osm) (exit)))

  (setq res (mg:cutwin p1 p2 (mg:2d target) scl nil))

  ;; תיחקות קו הפנים נעשית **כאן, על התוכנית המקורית** — לא אחר כך על
  ;; הגזירה. ‎-BOUNDARY אינו מתחקה לתוך בלוק גזור (XCLIP), ולכן ניסיון
  ;; לתחקות את הגזירה נכשל. הפוליגון נשמר ומועבר למערכת הנספח.
  (if res
    (progn
      (princ "\nעכשיו לחץ בתוך המרחב המוגן **בתוכנית המקורית**")
      (princ "\n(זה מה שיאפשר מידות, שטח ונפח. Enter לדלג.)")
      (setq ipt (getpoint "\n  נקודה בתוך המרחב: "))
      (if ipt
        (progn
          (setq wpts (mg:bpoly (mg:2d ipt)))
          (if wpts
            (progn
              (princ (strcat "\n  קו גולמי: " (itoa (length wpts)) " צלעות"))
              (setq wpts (mg:simplify wpts 15.0 (/ (* 4.0 pi) 180.0)))
              (setq wpts (car (mg:ccw wpts nil)))
              (princ (strcat "\n  אחרי ניקוי: " (itoa (length wpts)) " צלעות"))
              (setq bb (mg:bbox wpts))
              (princ (strcat "\n  תיבה חוסמת: " (rtos (- (caddr bb) (car bb)) 2 1)
                             " x " (rtos (- (cadddr bb) (cadr bb)) 2 1) " ס\"מ"))
              (princ (strcat "\n  שטח נטו   : "
                             (rtos (/ (abs (mg:sarea wpts)) 10000.0) 2 2) " מ\"ר"))
              ;; שמירה בקואורדינטות הנספח
              (setq base (list (/ (+ (car p1) (car p2)) 2.0)
                               (/ (+ (cadr p1) (cadr p2)) 2.0)))
              (setq apts (mapcar '(lambda (q) (mg:xf q base (mg:2d target) scl))
                                 wpts))
              (setq *MG-CUTS* (cons (list (cdr (assoc 2 (entget res)))
                                          apts scl)
                                    *MG-CUTS*))
              (princ "\n  נשמר. MMDDIM יוסיף מידות, שטח ונפח."))
            (progn
              (princ "\n  !! לא נסגר קו פנים. הגזירה עצמה תקינה —")
              (princ "\n     תוכל להריץ MMDDIM ולסמן את הפינות ידנית.")))))))

  (setvar "OSMODE" osm)
  (mapcar '(lambda (a b) (vl-catch-all-apply 'setvar (list a b))) sv vals)
  (if res
    (princ "\n=== הגזירה בנספח. MMDDRAW יוסיף מידות ואבזור מעליה. ===")
    (princ "\n=== לא נוצרה גזירה. ==="))
  (princ))

;;; שטח מסומן (shoelace). חיובי = נגד כיוון השעון.
(defun mg:sarea (pts / n i a p q)
  (setq n (length pts) i 0 a 0.0)
  (while (< i n)
    (setq p (nth i pts) q (nth (rem (1+ i) n) pts))
    (setq a (+ a (- (* (car p) (cadr q)) (* (car q) (cadr p)))))
    (setq i (1+ i)))
  (/ a 2.0))

;;; הפוליגון תמיד נגד כיוון השעון — כך "החוצה" הוא תמיד ימינה מכיוון הצלע
(defun mg:ccw (pts th / )
  (if (< (mg:sarea pts) 0.0)
    ;; היפוך: הצלעות מתהפכות, ולכן גם רשימת העוביים מוסטת
    (list (reverse pts)
          (if th (reverse (cons (car th) (reverse (cdr th)))) th))
    (list pts th)))

;;; (pts th) לכל רשומה. רשומה ישנה (בלי nth 9) מסונתזת ממלבן.
;;; סדר הצלעות במלבן: 0=דרום 1=מזרח 2=צפון 3=מערב
(defun mg:poly (rec / pts th L W tt)
  (if (setq pts (nth 9 rec))
    (mg:ccw pts (nth 10 rec))
    (progn
      (setq L (nth 1 rec) W (nth 2 rec) tt (nth 4 rec))
      (list (list (list 0.0 0.0) (list L 0.0) (list L W) (list 0.0 W))
            (list (nth 2 tt) (nth 1 tt) (nth 0 tt) (nth 3 tt))))))

;;; תיבה חוסמת של הפוליגון: (xmin ymin xmax ymax)
(defun mg:bbox (pts / xs ys)
  (setq xs (mapcar 'car pts) ys (mapcar 'cadr pts))
  (list (apply 'min xs) (apply 'min ys) (apply 'max xs) (apply 'max ys)))

;;; חיתוך שני ישרים אינסופיים p+t*r ו-q+s*w. nil כשהם מקבילים.
(defun mg:xline (p r q w / d t1)
  (setq d (- (* (car r) (cadr w)) (* (cadr r) (car w))))
  (if (< (abs d) 1e-9)
    nil
    (progn
      (setq t1 (/ (- (* (- (car q) (car p)) (cadr w))
                     (* (- (cadr q) (cadr p)) (car w))) d))
      (list (+ (car p) (* (car r) t1)) (+ (cadr p) (* (cadr r) t1))))))

;;; הפוליגון החיצוני: כל צלע מוסטת החוצה בעובייה, והפינות הן חיתוך
;;; הישרים המוסטים. כך פינות קמורות וקעורות יוצאות נכון גם כשהעוביים
;;; שונים — בלי זה קירות בעובי שונה נחתכים זה בזה בפינה.
(defun mg:outer (pts th / n i j o dir nrm p q res pi1 pj1 dj nj x)
  (setq n (length pts) i 0 res '())
  (while (< i n)
    ;; פינה i היא מפגש צלע i-1 וצלע i
    (setq j (rem (+ i (1- n)) n))                   ; הצלע הקודמת
    (setq p (nth j pts) pi1 (nth (rem (1+ j) n) pts))
    (setq dir (list (- (car pi1) (car p)) (- (cadr pi1) (cadr p))))
    (setq nrm (vnorm (list (cadr dir) (- (car dir)))))   ; ימינה = החוצה
    (setq p (list (+ (car p) (* (car nrm) (nth j th)))
                  (+ (cadr p) (* (cadr nrm) (nth j th)))))
    (setq q (nth i pts) pj1 (nth (rem (1+ i) n) pts))
    (setq dj (list (- (car pj1) (car q)) (- (cadr pj1) (cadr q))))
    (setq nj (vnorm (list (cadr dj) (- (car dj)))))
    (setq q (list (+ (car q) (* (car nj) (nth i th)))
                  (+ (cadr q) (* (cadr nj) (nth i th)))))
    (setq x (mg:xline p dir q dj))
    (setq res (cons (if x x q) res))
    (setq i (1+ i)))
  (reverse res))

;;; הצללה של מצולע כלשהו בקווי 45° — הכללה של mg:hatch למרובעים נטויים
(defun mg:hpoly (ly pts sp / bb x0 y0 x1 y1 step c cs xs n i p q d t1 t2 hits)
  (setq bb (mg:bbox pts) x0 (car bb) y0 (cadr bb) x1 (caddr bb) y1 (cadddr bb))
  (setq step (* sp (sqrt 2.0)))
  (setq c (* step (float (fix (/ (- y0 x1) step)))))
  (while (< c (- y1 x0))
    ;; הישר y = x + c ; מוצאים חיתוכים עם צלעות המצולע
    (setq hits '() n (length pts) i 0)
    (while (< i n)
      (setq p (nth i pts) q (nth (rem (1+ i) n) pts))
      (setq d (- (- (cadr q) (car q)) (- (cadr p) (car p))))
      (if (> (abs d) 1e-9)
        (progn
          (setq t1 (/ (- c (- (cadr p) (car p))) d))
          (if (and (>= t1 -1e-9) (<= t1 1.000000001))
            (setq hits (cons (+ (car p) (* t1 (- (car q) (car p)))) hits)))))
      (setq i (1+ i)))
    (setq hits (vl-sort hits '<))
    (while (>= (length hits) 2)
      (setq t1 (car hits) t2 (cadr hits))
      (if (> (- t2 t1) 0.01)
        (mg:line ly (list t1 (+ t1 c)) (list t2 (+ t2 c))))
      (setq hits (cddr hits)))
    (setq c (+ c step)))
  nil)

(defun mg:op-z (op)  ; טווח גבהים של פתח: (z0 z1)
  (cond ((= (car op) "win")  (list (nth 5 op) (+ (nth 5 op) (nth 4 op))))
        ((= (car op) "vent") (list (- (nth 5 op) (/ (nth 4 op) 2.0))
                                   (+ (nth 5 op) (/ (nth 4 op) 2.0))))
        (T (list 0.0 (nth 4 op)))))

;;; פיצול צלע לקטעים מלאים סביב פתחיה. מחזיר רשימת (a b) לאורך הצלע
(defun mg:wallsegs (lo hi ops side / xs cur segs o a b)
  (setq xs '())
  (foreach o ops
    (if (= (cadr o) side)
      (setq xs (cons (list (caddr o) (+ (caddr o) (cadddr o))) xs))))
  (setq xs (vl-sort xs '(lambda (a b) (< (car a) (car b)))))
  (setq cur lo segs '())
  (foreach o xs
    (setq a (car o) b (cadr o))
    (if (> a cur) (setq segs (cons (list cur a) segs)))
    (setq cur (max cur b)))
  (if (> hi cur) (setq segs (cons (list cur hi) segs)))
  (reverse segs))

;;; ציור תוכנית של מרחב אחד; ox,oy = ראשית הפנים
(defun mg:plan (rec ox oy th hatch? / id L W H tt tN tE tS tW tC tF ops
                s a b f side off opw hgt hinge sh dir lw px py cx cy dia
                pts d1 d2 d3)
  (setq id (nth 0 rec) L (nth 1 rec) W (nth 2 rec) H (nth 3 rec)
        tt (nth 4 rec) tC (nth 5 rec) tF (nth 6 rec) ops (nth 7 rec))
  (setq tN (nth 0 tt) tE (nth 1 tt) tS (nth 2 tt) tW (nth 3 tt))

  ;; קירות מפוצלים סביב פתחים — ארבע צלעות
  (foreach s (mg:wallsegs (- tW) (+ L tE) ops "S")
    (mg:hrect "WALL" "HATCH" (+ ox (car s)) (- oy tS) (+ ox (cadr s)) oy 8.0 hatch?))
  (foreach s (mg:wallsegs (- tW) (+ L tE) ops "N")
    (mg:hrect "WALL" "HATCH" (+ ox (car s)) (+ oy W) (+ ox (cadr s)) (+ oy W tN) 8.0 hatch?))
  (foreach s (mg:wallsegs 0.0 W ops "W")
    (mg:hrect "WALL" "HATCH" (- ox tW) (+ oy (car s)) ox (+ oy (cadr s)) 8.0 hatch?))
  (foreach s (mg:wallsegs 0.0 W ops "E")
    (mg:hrect "WALL" "HATCH" (+ ox L) (+ oy (car s)) (+ ox L tE) (+ oy (cadr s)) 8.0 hatch?))

  ;; פתחים
  (foreach f ops
    (setq side (cadr f) off (caddr f) opw (cadddr f) hgt (nth 4 f) hinge (nth 6 f))
    ;; מסגרת מקומית של הצלע: פאה פנימית in?out
    (cond
      ((= side "S") (setq px (+ ox off) py oy       dir '(0 -1) lw tS))
      ((= side "N") (setq px (+ ox off) py (+ oy W) dir '(0 1)  lw tN))
      ((= side "W") (setq px ox py (+ oy off)       dir '(-1 0) lw tW))
      ((= side "E") (setq px (+ ox L) py (+ oy off) dir '(1 0)  lw tE)))
    (setq d1 (if (or (= side "S") (= side "N")) '(1 0) '(0 1)))  ; לאורך הקיר

    (cond
      ((= (car f) "door") (mg:dr-door px py d1 dir lw opw hinge))
      ((= (car f) "win")  (mg:dr-win  px py d1 dir lw opw))
      (T                  (mg:dr-vent px py d1 dir lw opw))))

  ;; כיתוב מרכזי: שם, שטח, נפח — בתוך המרחב עצמו
  (mg:text "TEXT" (list (+ ox (/ L 2.0)) (+ oy (/ W 2.0) (* th 1.9))) (* th 1.5) id 1 0)
  (mg:text "TEXT" (list (+ ox (/ L 2.0)) (+ oy (/ W 2.0) (* th 0.1))) th
           (strcat (rtos (mg:area rec) 2 2) " \U+05DE\"\U+05E8") 1 0)
  (mg:text "TEXT" (list (+ ox (/ L 2.0)) (+ oy (/ W 2.0) (* th -1.6))) th
           (strcat (rtos (mg:vol rec) 2 2) " \U+05DE\"\U+05E7") 1 0)

  ;; מידות + בלוק נתונים צמוד לתוכנית (במקום טבלה מרכזת)
  (mg:dims rec ox oy)
  (mg:info rec ox oy th))

;;; שטח נטו במ"ר ונפח נטו במ"ק — הקלט בס"מ.
;;; מחושבים מהפוליגון, כך שממ"ד בצורת ר' מקבל את שטחו האמיתי ולא
;;; את שטח התיבה החוסמת.
(defun mg:area (rec) (/ (abs (mg:sarea (car (mg:poly rec)))) 10000.0))
(defun mg:vol  (rec) (* (mg:area rec) (/ (nth 3 rec) 100.0)))

;;; היקף פנים — זה ה-L של חישוב ירידת קירות ב-RULES.md
(defun mg:perim (rec / pts n i p q s)
  (setq pts (car (mg:poly rec)) n (length pts) i 0 s 0.0)
  (while (< i n)
    (setq p (nth i pts) q (nth (rem (1+ i) n) pts))
    (setq s (+ s (distance p q)))
    (setq i (1+ i)))
  s)

;;; עובי המילוי/ריצוף. נשמר בסוף הרשומה, כך שרשומות ישנות (בלי השדה)
;;; עדיין נטענות — nth מחזיר nil ואז נופלים לברירת המחדל.
(defun mg:fill (rec / v) (if (setq v (nth 8 rec)) v *MG-FILL*))

;;; בלוק נתונים מתחת לתוכנית של אותו מרחב.
;;; המשתמש ביקש שלא תהיה טבלה מרכזת — כל האינפורמציה על הממ"ד עצמו.
(defun mg:info (rec ox oy th / tt y sw d1 o lin)
  (setq tt (nth 4 rec))
  (setq d1 (* 2.5 (getvar "DIMTXT") (getvar "DIMSCALE")))
  ;; הבלוק חייב לשבת מתחת לכל מה שבולט כלפי מטה: שרשרת המידות
  ;; החיצונית, הכוללת, וקשת הדלת הדרומית (שרדיוסה כרוחב הדלת).
  (setq sw 0.0)
  (foreach o (nth 7 rec)
    (if (and (= (car o) "door") (= (cadr o) "S"))
      (setq sw (max sw (cadddr o)))))
  (setq y (- oy (nth 2 tt) (max (* 3.0 d1) (+ sw (* 2.0 th))) (* 2.0 th)))
  (defun lin (s) (mg:text "TEXT" (list ox y) (* th 0.9) s 0 0)
                 (setq y (- y (* th 1.7))))
  (lin (strcat "\U+05E4\U+05E0\U+05D9\U+05DD " (rtos (nth 1 rec) 2 0) "/" (rtos (nth 2 rec) 2 0)
               " \U+05D2\U+05D5\U+05D1\U+05D4 " (rtos (nth 3 rec) 2 0)))
  (lin (strcat "\U+05E7\U+05D9\U+05E8\U+05D5\U+05EA \U+05E6/\U+05DE\U+05D6/\U+05D3/\U+05DE\U+05E2 "
               (rtos (nth 0 tt) 2 0) "/" (rtos (nth 1 tt) 2 0) "/"
               (rtos (nth 2 tt) 2 0) "/" (rtos (nth 3 tt) 2 0)))
  (lin (strcat "\U+05EA\U+05E7\U+05E8\U+05D4 " (rtos (nth 5 rec) 2 0)
               " \U+05E8\U+05E6\U+05E4\U+05D4 " (rtos (nth 6 rec) 2 0)
               " \U+05DE\U+05D9\U+05DC\U+05D5\U+05D9 " (rtos (mg:fill rec) 2 0)))
  (lin (strcat "\U+05D3\U+05DC\U+05EA " (mg:opdesc rec "door")
               "  \U+05D7\U+05DC\U+05D5\U+05DF " (mg:opdesc rec "win")))
  y)

;;; דלת: כנף + קשת. hinge "A" = בקצה off, "B" = בקצה off+w. תמיד החוצה.
(defun mg:dr-door (px py d1 dir lw w hinge / hx hy ux uy leaf a0 a1 tx ty)
  ;; קו סף על הפאה החיצונית
  (mg:line "DOOR" (list px py)
           (list (+ px (* (car d1) w)) (+ py (* (cadr d1) w))))
  ;; נקודת ציר על הפאה החיצונית
  (if (= hinge "A")
    (setq hx (+ px (* (car dir) lw)) hy (+ py (* (cadr dir) lw)) ux (car d1) uy (cadr d1))
    (setq hx (+ px (* (car d1) w) (* (car dir) lw))
          hy (+ py (* (cadr d1) w) (* (cadr dir) lw))
          ux (- (car d1)) uy (- (cadr d1))))
  ;; כנף בזווית 90 החוצה
  (setq leaf 5.0)
  (mg:pline "DOOR"
    (list (list hx hy)
          (list (+ hx (* (car dir) w)) (+ hy (* (cadr dir) w)))
          (list (+ hx (* (car dir) w) (* ux leaf)) (+ hy (* (cadr dir) w) (* uy leaf)))
          (list (+ hx (* ux leaf)) (+ hy (* uy leaf)))) T)
  ;; קשת מהכנף אל הקיר
  (setq a0 (atan (cadr dir) (car dir)))
  (setq a1 (atan uy ux))
  (if (> (rem (+ (- a1 a0) (* 4 pi)) (* 2 pi)) pi)
    (mg:arc "DOOR" (list hx hy) w a1 a0)
    (mg:arc "DOOR" (list hx hy) w a0 a1)))

;;; חלון: שני קווי הפאות + שני קווים פנימיים
(defun mg:dr-win (px py d1 dir lw w / k p1 p2)
  (foreach k '(0.0 0.35 0.65 1.0)
    (setq p1 (list (+ px (* (car dir) lw k)) (+ py (* (cadr dir) lw k))))
    (setq p2 (list (+ (car p1) (* (car d1) w)) (+ (cadr p1) (* (cadr d1) w))))
    (mg:line "WINDOW" p1 p2)))

;;; צינור: קווי פאות + עיגול
(defun mg:dr-vent (px py d1 dir lw w / p1 p2 c)
  (foreach k '(0.0 1.0)
    (setq p1 (list (+ px (* (car dir) lw k)) (+ py (* (cadr dir) lw k))))
    (setq p2 (list (+ (car p1) (* (car d1) w)) (+ (cadr p1) (* (cadr d1) w))))
    (mg:line "VENT" p1 p2))
  (setq c (list (+ px (* (car d1) w 0.5) (* (car dir) lw 0.5))
                (+ py (* (cadr d1) w 0.5) (* (cadr dir) lw 0.5))))
  (mg:circle "VENT" c (* w 0.5)))

;;; מידות לתוכנית.
;;; המשתמש ביקש (27.08.2026) שמידות הפנים יופיעו **בתוך** המרחב, ושלכל
;;; קיר תהיה מידת עובי משלו. לכן:
;;;   פנימי  — אורך ורוחב נטו, קווי המידה בתוך החדר
;;;   חיצוני — שרשרת הפתחים בצלע הדרומית + כוללת חוץ
;;;   עוביים — מידה קצרה לכל אחד מארבעת הקירות
(defun mg:dims (rec ox oy / L W tt tN tE tS tW ops xs prev x d1 d2 ins)
  (setq L (nth 1 rec) W (nth 2 rec) tt (nth 4 rec) ops (nth 7 rec))
  (setq tN (nth 0 tt) tE (nth 1 tt) tS (nth 2 tt) tW (nth 3 tt))
  (setq d1 (* 2.5 (getvar "DIMTXT") (getvar "DIMSCALE")) d2 (* 2.0 d1))
  ;; מרחק קו המידה הפנימי מפאת הקיר — לא יותר מרבע החדר, שלא ייצא החוצה
  (setq ins (min d1 (* 0.25 (min L W))))

  ;; ---- מידות פנים, בתוך החדר ----
  (mg:dim T   (list ox oy) (list (+ ox L) oy)
              (list (+ ox (/ L 2.0)) (+ oy ins)))
  (mg:dim nil (list ox oy) (list ox (+ oy W))
              (list (+ ox ins) (+ oy (/ W 2.0))))

  ;; ---- שרשרת דרום: פינות + פתחי הצלע ----
  (setq xs (list 0.0 L))
  (foreach o ops
    (if (= (cadr o) "S")
      (setq xs (append xs (list (caddr o) (+ (caddr o) (cadddr o)))))))
  (setq xs (vl-sort xs '<))
  (setq prev (car xs))
  (foreach x (cdr xs)
    (if (> (- x prev) 0.01)
      (mg:dim T (list (+ ox prev) (- oy tS)) (list (+ ox x) (- oy tS))
                (list (+ ox (/ (+ prev x) 2.0)) (- oy tS d1))))
    (setq prev x))
  ;; כוללת חוץ
  (mg:dim T (list (- ox tW) (- oy tS)) (list (+ ox L tE) (- oy tS))
            (list (+ ox (/ L 2.0)) (- oy tS d2)))
  (mg:dim nil (list (- ox tW) (- oy tS)) (list (- ox tW) (+ oy W tN))
              (list (- ox tW d2) (+ oy (/ W 2.0))))

  ;; ---- עובי כל קיר בנפרד ----
  ;; דרום ומזרח: קו המידה מוסט הצידה כדי לא להתנגש בשרשרת ובכוללת
  (mg:dim nil (list (+ ox (* 0.25 L)) (- oy tS)) (list (+ ox (* 0.25 L)) oy)
              (list (+ ox (* 0.25 L)) (- oy (/ tS 2.0))))
  (mg:dim nil (list (+ ox (* 0.75 L)) (+ oy W)) (list (+ ox (* 0.75 L)) (+ oy W tN))
              (list (+ ox (* 0.75 L)) (+ oy W (/ tN 2.0))))
  (mg:dim T   (list (- ox tW) (+ oy (* 0.75 W))) (list ox (+ oy (* 0.75 W)))
              (list (- ox (/ tW 2.0)) (+ oy (* 0.75 W))))
  (mg:dim T   (list (+ ox L) (+ oy (* 0.25 W))) (list (+ ox L tE) (+ oy (* 0.25 W)))
              (list (+ ox L (/ tE 2.0)) (+ oy (* 0.25 W)))))

;;; חתך של מרחב אחד: רצפה, תקרה, קירות מזרח/מערב, פתחי צפון/דרום מקווקווים
;;; שרשרת המידות של החתך — לפי בקשת המשתמש, 27.08.2026:
;;; רצפת בטון · מילוי · מהריצוף עד אדן החלון · גובה החלון · מראש החלון
;;; עד פני התקרה · תקרת בטון. הרמות נגזרות מהפתחים עצמם, כך שכל פתח
;;; נוסף (צינור אוורור למשל) מקבל את המידות שלו אוטומטית.
(defun mg:secdims (rec ox oy / H tt tE tW tC tF fl xr xl xo n zs prev z d1 d2 o zz)
  (setq H (nth 3 rec) tt (nth 4 rec) tC (nth 5 rec) tF (nth 6 rec)
        fl (mg:fill rec))
  (setq tE (nth 1 tt) tW (nth 3 tt))
  (setq d1 (* 2.5 (getvar "DIMTXT") (getvar "DIMSCALE")) d2 (* 2.0 d1))
  (setq xr (- ox tW))                  ; פאה שמאלית — שרשראות הפתחים
  (setq xl (+ ox (nth 1 rec) tE))      ; פאה ימנית — מבנה הרצפה והצנרת

  ;; שרשרת נפרדת לכל פתח, במרחק הולך וגדל מהקיר.
  ;; למה לא שרשרת אחת: ראש דלת בגובה 200 וראש חלון בגובה 205 יוצרים
  ;; קטע של 5 ס"מ, והטקסט נערם על שכנו. לאחד את הרמות היה מזייף מידה
  ;; בשרטוט טכני — ולכן כל פתח מקבל שרשרת משלו, וכולן נקראות.
  (setq n 0)
  (foreach o (nth 7 rec)
    (if (/= (car o) "vent")
      (progn
        (setq zz (mg:op-z o))
        (setq zs (vl-sort (list 0.0 (car zz) (cadr zz) H) '<))
        (setq xo (- xr (* d1 (1+ n))))
        (setq prev (car zs))
        (foreach z (cdr zs)
          (if (> (- z prev) 0.01)
            (mg:dim nil (list xr (+ oy prev)) (list xr (+ oy z))
                        (list xo (+ oy (/ (+ prev z) 2.0)))))
          (setq prev z))
        (setq n (1+ n)))))
  ;; אין פתחים בכלל — לפחות גובה הפנים
  (if (= n 0)
    (progn (mg:dim nil (list xr oy) (list xr (+ oy H))
                       (list (- xr d1) (+ oy (/ H 2.0))))
           (setq n 1)))

  ;; תקרת בטון — על השרשרת הראשונה
  (mg:dim nil (list xr (+ oy H)) (list xr (+ oy H tC))
              (list (- xr d1) (+ oy H (/ tC 2.0))))
  ;; גובה פנים נטו וגובה כולל — מעבר לכל השרשראות
  (mg:dim nil (list xr oy) (list xr (+ oy H))
              (list (- xr (* d1 (+ n 1))) (+ oy (/ H 2.0))))
  (mg:dim nil (list xr (- oy fl tF)) (list xr (+ oy H tC))
              (list (- xr (* d1 (+ n 2))) (+ oy (/ H 2.0))))

  ;; ---- צד ימין: רצפת בטון, מילוי, וגובה ציר כל צינור ----
  (mg:dim nil (list xl (- oy fl tF)) (list xl (- oy fl))
              (list (+ xl d1) (- oy fl (/ tF 2.0))))
  (if (> fl 0.01)
    (mg:dim nil (list xl (- oy fl)) (list xl oy)
                (list (+ xl d2) (- oy (/ fl 2.0)))))
  (foreach o (nth 7 rec)
    (if (= (car o) "vent")
      (mg:dim nil (list xl oy) (list xl (+ oy (nth 5 o)))
                  (list (+ xl d1) (+ oy (/ (nth 5 o) 2.0))))))
  ;; אופקי: פנים + עובי שני הקירות
  (mg:dim T (list ox (+ oy H tC)) (list (+ ox (nth 1 rec)) (+ oy H tC))
            (list (+ ox (/ (nth 1 rec) 2.0)) (+ oy H tC d1)))
  (mg:dim T (list (- ox tW) (+ oy H tC)) (list ox (+ oy H tC))
            (list (- ox (/ tW 2.0)) (+ oy H tC d2)))
  (mg:dim T (list (+ ox (nth 1 rec)) (+ oy H tC))
            (list (+ ox (nth 1 rec) tE) (+ oy H tC))
            (list (+ ox (nth 1 rec) (/ tE 2.0)) (+ oy H tC d2))))

(defun mg:section (rec ox oy th hatch? / id L W H tt tE tW tC tF fl ops s z f)
  (setq id (nth 0 rec) L (nth 1 rec) H (nth 3 rec)
        tt (nth 4 rec) tC (nth 5 rec) tF (nth 6 rec) ops (nth 7 rec))
  (setq tE (nth 1 tt) tW (nth 3 tt) fl (mg:fill rec))
  ;; רצפה: מילוי/ריצוף מעל, רצפת בטון מתחתיו. oy = פני הריצוף הגמור.
  (mg:hrect "SECTION" "HATCH" (- ox tW) (- oy fl tF) (+ ox L tE) (- oy fl) 8.0 hatch?)
  (mg:rect  "SECTION" (- ox tW) (- oy fl) (+ ox L tE) oy)
  (mg:hrect "SECTION" "HATCH" (- ox tW) (+ oy H) (+ ox L tE) (+ oy H tC) 8.0 hatch?)
  ;; קירות צד עם פתחיהם
  (foreach s (mg:vsegs rec "W") 
    (mg:hrect "SECTION" "HATCH" (- ox tW) (+ oy (car s)) ox (+ oy (cadr s)) 8.0 hatch?))
  (foreach s (mg:vsegs rec "E")
    (mg:hrect "SECTION" "HATCH" (+ ox L) (+ oy (car s)) (+ ox L tE) (+ oy (cadr s)) 8.0 hatch?))
  ;; פתחי הקירות הניצבים — קו נסתר
  (foreach f (nth 7 rec)
    (if (or (= (cadr f) "N") (= (cadr f) "S"))
      (progn
        (setq z (mg:op-z f))
        (mg:rect "HIDDEN" (+ ox (caddr f)) (+ oy (car z))
                          (+ ox (caddr f) (cadddr f)) (+ oy (cadr z))))))
  ;; מידות
  (mg:secdims rec ox oy)
  ;; מפלס
  (mg:pline "SECTION" (list (list (+ ox (* 0.5 L)) oy)
                            (list (+ ox (* 0.5 L) -6.0) (- oy 10.0))
                            (list (+ ox (* 0.5 L) 6.0) (- oy 10.0))) T)
  (mg:text "TEXT" (list (+ ox (* 0.5 L) 10.0) (+ oy (* th 0.3))) th "%%p0.00" 0 0)
  (mg:text "TEXT" (list (+ ox (/ L 2.0)) (- oy fl tF (* th 2.5))) (* th 1.2)
           (strcat "\U+05D7\U+05EA\U+05DA " id) 1 0))

;;; קטעי קיר אנכיים בחתך (פתחי אותה צלע)
(defun mg:vsegs (rec side / H ops zs cur segs o z)
  (setq H (nth 3 rec) ops (nth 7 rec))
  (setq zs '())
  (foreach o ops
    (if (= (cadr o) side) (setq zs (cons (mg:op-z o) zs))))
  (setq zs (vl-sort zs '(lambda (a b) (< (car a) (car b)))))
  (setq cur 0.0 segs '())
  (foreach z zs
    (if (> (car z) cur) (setq segs (cons (list cur (car z)) segs)))
    (setq cur (max cur (cadr z))))
  (if (> H cur) (setq segs (cons (list cur H) segs)))
  (reverse segs))

;;; טבלה מרכזת
(defun mg:table (ox oy th / rh cw cols x y r tt vals c i totw)
  (setq rh (* th 2.0))
  (setq cols (list (list "\U+05DE\U+05E1'" 14.0) (list "\U+05DE\U+05D9\U+05D3\U+05D5\U+05EA \U+05E4\U+05E0\U+05D9\U+05DD" 26.0)
                   (list "\U+05E9\U+05D8\U+05D7 \U+05DE\"\U+05E8" 16.0) (list "\U+05D2\U+05D5\U+05D1\U+05D4" 12.0)
                   (list "\U+05E7\U+05D9\U+05E8\U+05D5\U+05EA \U+05E6/\U+05DE\U+05D6/\U+05D3/\U+05DE\U+05E2" 30.0)
                   (list "\U+05EA\U+05E7\U+05E8\U+05D4/\U+05E8\U+05E6\U+05E4\U+05D4" 20.0) (list "\U+05D3\U+05DC\U+05EA" 16.0)
                   (list "\U+05D7\U+05DC\U+05D5\U+05DF" 16.0)))
  (setq cols (mapcar '(lambda (c) (list (car c) (* (cadr c) th 0.7))) cols))
  (setq totw (apply '+ (mapcar 'cadr cols)))
  ;; כותרת
  (mg:text "TEXT" (list (- ox (/ totw 2.0)) (+ oy th)) (* th 1.3)
           "\U+05D8\U+05D1\U+05DC\U+05EA \U+05DE\U+05E8\U+05D7\U+05D1\U+05D9\U+05DD \U+05DE\U+05D5\U+05D2\U+05E0\U+05D9\U+05DD" 1 0)
  ;; שורת כותרות (מימין לשמאל: הטור הראשון בימין)
  (setq y oy i 0)
  (mg:trow ox y cols rh (mapcar 'car cols))
  (setq y (- y rh))
  (foreach r *MMD-LIST*
    (setq tt (nth 4 r))
    (setq vals (list
      (nth 0 r)
      (strcat (rtos (nth 1 r) 2 0) "x" (rtos (nth 2 r) 2 0))
      (rtos (/ (* (nth 1 r) (nth 2 r)) 10000.0) 2 2)
      (rtos (nth 3 r) 2 0)
      (strcat (rtos (nth 0 tt) 2 0) "/" (rtos (nth 1 tt) 2 0) "/"
              (rtos (nth 2 tt) 2 0) "/" (rtos (nth 3 tt) 2 0))
      (strcat (rtos (nth 5 r) 2 0) "/" (rtos (nth 6 r) 2 0))
      (mg:opdesc r "door") (mg:opdesc r "win")))
    (mg:trow ox y cols rh vals)
    (setq y (- y rh)))
  (- oy y))

(defun mg:opdesc (rec typ / o out)
  (setq out "-")
  (foreach o (nth 7 rec)
    (if (= (car o) typ)
      (setq out (strcat (rtos (cadddr o) 2 0) "/" (rtos (nth 4 o) 2 0)))))
  out)

;;; שורת טבלה: תאים מימין לשמאל
(defun mg:trow (ox y cols rh vals / x c v th)
  (setq th (* 0.4 rh))
  (setq x ox)
  (mapcar
    '(lambda (c v)
       (mg:rect "TABLE" (- x (cadr c)) (- y rh) x y)
       (mg:text "TEXT" (list (- x (/ (cadr c) 2.0)) (- y (* rh 0.68))) th v 1 0)
       (setq x (- x (cadr c))))
    cols vals)
  nil)

;;; הערות
(defun mg:notes (ox oy th / i y n)
  (mg:text "TEXT" (list ox (+ oy th)) (* th 1.3) "\U+05D4\U+05E2\U+05E8\U+05D5\U+05EA \U+05DB\U+05DC\U+05DC\U+05D9\U+05D5\U+05EA" 2 0)
  (setq i 1 y (- oy (* th 1.2)))
  (foreach n *MG-NOTES*
    (mg:text "TEXT" (list ox y) (* th 0.85) (strcat (itoa i) ". " n) 2 0)
    (setq y (- y (* th 1.9)) i (1+ i)))
  (- oy y))

(setq *MG-NOTES* (list
  "\U+05D4\U+05D1\U+05D9\U+05E6\U+05D5\U+05E2 \U+05D1\U+05D4\U+05EA\U+05D0\U+05DD \U+05DC\U+05EA\U+05E7\U+05E0\U+05D5\U+05EA \U+05D4\U+05D4\U+05EA\U+05D2\U+05D5\U+05E0\U+05E0\U+05D5\U+05EA \U+05D4\U+05D0\U+05D6\U+05E8\U+05D7\U+05D9\U+05EA (\U+05DE\U+05E4\U+05E8\U+05D8\U+05D9\U+05DD \U+05DC\U+05D1\U+05E0\U+05D9\U+05D9\U+05EA \U+05DE\U+05E7\U+05DC\U+05D8\U+05D9\U+05DD) \U+05D5\U+05DC\U+05D4\U+05E0\U+05D7\U+05D9\U+05D5\U+05EA \U+05E4\U+05D9\U+05E7\U+05D5\U+05D3 \U+05D4\U+05E2\U+05D5\U+05E8\U+05E3 \U+05D4\U+05EA\U+05E7\U+05E4\U+05D5\U+05EA \U+05DC\U+05DE\U+05D5\U+05E2\U+05D3 \U+05D4\U+05D4\U+05D9\U+05EA\U+05E8."
  "\U+05DB\U+05DC \U+05D4\U+05E7\U+05D9\U+05E8\U+05D5\U+05EA, \U+05D4\U+05EA\U+05E7\U+05E8\U+05D4 \U+05D5\U+05D4\U+05E8\U+05E6\U+05E4\U+05D4 \U+05E9\U+05DC \U+05D4\U+05DE\U+05E8\U+05D7\U+05D1 \U+05D4\U+05DE\U+05D5\U+05D2\U+05DF \U+05DE\U+05D1\U+05D8\U+05D5\U+05DF \U+05DE\U+05D6\U+05D5\U+05D9\U+05DF \U+05D9\U+05E6\U+05D5\U+05E7 \U+05D1\U+05D0\U+05EA\U+05E8."
  "\U+05DE\U+05E2\U+05E8\U+05DB\U+05D5\U+05EA \U+05D4\U+05D0\U+05D5\U+05D5\U+05E8\U+05D5\U+05E8 \U+05D5\U+05D4\U+05E1\U+05D9\U+05E0\U+05D5\U+05DF \U+05D9\U+05D5\U+05EA\U+05E7\U+05E0\U+05D5 \U+05D1\U+05D4\U+05EA\U+05D0\U+05DD \U+05DC\U+05D3\U+05E8\U+05D9\U+05E9\U+05D5\U+05EA \U+05EA\"\U+05D9 4570."
  "\U+05D0\U+05D9\U+05DF \U+05DC\U+05D4\U+05E2\U+05D1\U+05D9\U+05E8 \U+05D3\U+05E8\U+05DA \U+05E7\U+05D9\U+05E8\U+05D5\U+05EA \U+05D4\U+05DE\U+05E8\U+05D7\U+05D1 \U+05D4\U+05DE\U+05D5\U+05D2\U+05DF \U+05E6\U+05E0\U+05E8\U+05EA \U+05E9\U+05D0\U+05D9\U+05E0\U+05D4 \U+05DE\U+05E9\U+05DE\U+05E9\U+05EA \U+05D0\U+05EA \U+05E6\U+05D5\U+05E8\U+05DB\U+05D9 \U+05D4\U+05DE\U+05E8\U+05D7\U+05D1 \U+05D4\U+05DE\U+05D5\U+05D2\U+05DF."
  "\U+05D9\U+05D5\U+05EA\U+05E7\U+05DF \U+05E6\U+05D9\U+05E0\U+05D5\U+05E8 \U+05DE\U+05E2\U+05D1\U+05E8 \U+05DB\U+05D1\U+05D9\U+05DC\U+05D4 \U+05DE\U+05D4\U+05DE\U+05DE\"\U+05D3 \U+05D0\U+05DC \U+05D4\U+05D3\U+05D9\U+05E8\U+05D4 \U+05D1\U+05D4\U+05EA\U+05D0\U+05DD \U+05DC\U+05D4\U+05E0\U+05D7\U+05D9\U+05D5\U+05EA \U+05E4\U+05E7\U+05E2\"\U+05E8."
  "\U+05D3\U+05DC\U+05EA \U+05D4\U+05D4\U+05D3\U+05E3 \U+05D5\U+05D7\U+05DC\U+05D5\U+05DF \U+05D4\U+05D4\U+05D3\U+05E3 \U+05D9\U+05D4\U+05D9\U+05D5 \U+05D1\U+05E2\U+05DC\U+05D9 \U+05EA\U+05D5 \U+05EA\U+05E7\U+05DF \U+05D5\U+05D0\U+05D9\U+05E9\U+05D5\U+05E8 \U+05E4\U+05D9\U+05E7\U+05D5\U+05D3 \U+05D4\U+05E2\U+05D5\U+05E8\U+05E3."
  "\U+05D3\U+05DC\U+05EA \U+05D4\U+05D4\U+05D3\U+05E3 \U+05E0\U+05E4\U+05EA\U+05D7\U+05EA \U+05D4\U+05D7\U+05D5\U+05E6\U+05D4."
  "\U+05D4\U+05DE\U+05D9\U+05D3\U+05D5\U+05EA \U+05D1\U+05EA\U+05D5\U+05DB\U+05E0\U+05D9\U+05EA \U+05D4\U+05DF \U+05DE\U+05D9\U+05D3\U+05D5\U+05EA \U+05E4\U+05E0\U+05D9\U+05DD \U+05E0\U+05D8\U+05D5 \U+05DC\U+05D0\U+05D7\U+05E8 \U+05D2\U+05DE\U+05E8."
  "\U+05D2\U+05D5\U+05D1\U+05D4 \U+05E4\U+05E0\U+05D9\U+05DD \U+05E0\U+05D8\U+05D5 250 \U+05E1\"\U+05DE \U+05DC\U+05E4\U+05D7\U+05D5\U+05EA \U+05D0\U+05D7\U+05E8\U+05D9 \U+05E8\U+05D9\U+05E6\U+05D5\U+05E3."
  "\U+05DB\U+05DC \U+05E1\U+05D8\U+05D9\U+05D9\U+05D4 \U+05DE\U+05D4\U+05DE\U+05E1\U+05D5\U+05DE\U+05DF \U+05D1\U+05E0\U+05E1\U+05E4\U+05D7 \U+05D6\U+05D4 \U+05D8\U+05E2\U+05D5\U+05E0\U+05D4 \U+05D0\U+05D9\U+05E9\U+05D5\U+05E8 \U+05DE\U+05D5\U+05E7\U+05D3\U+05DD \U+05E9\U+05DC \U+05D9\U+05D5\U+05E2\U+05E5 \U+05D4\U+05DE\U+05D9\U+05D2\U+05D5\U+05DF."))

;;; ---------- MMDDRAW ----------
(defun mg:sysvars () '("CMDECHO" "OSMODE" "BLIPMODE" "CLAYER" "TEXTSTYLE"
    "DIMSCALE" "DIMTXT" "DIMASZ" "DIMDEC" "DIMLFAC" "DIMTAD"
    "DIMTIH" "DIMTOH" "DIMEXE" "DIMEXO" "DIMGAP" "DIMBLK" "DIMSAH"
    "DIMATFIT" "DIMTMOVE" "DIMTOFL"))

(defun mg:setup (scl)
  (setvar "CMDECHO" 0) (setvar "OSMODE" 0) (setvar "BLIPMODE" 0)
  (setvar "TEXTSTYLE" (strcat *MG-PREFIX* "TXT"))
  (setvar "DIMSCALE" scl) (setvar "DIMTXT" 0.25)
  (setvar "DIMASZ" 0.25) (setvar "DIMEXE" 0.12) (setvar "DIMEXO" 0.1)
  (setvar "DIMGAP" 0.08) (setvar "DIMDEC" 0) (setvar "DIMLFAC" 1.0)
  (setvar "DIMTAD" 1) (setvar "DIMTIH" 0) (setvar "DIMTOH" 0) (setvar "DIMSAH" 0)
  ;; שרשרת המידות בחתך מכילה קטעים קצרים מאוד (למשל 5 ס"מ בין ראש
  ;; צינור לראש חלון). בלי אלה הטקסטים נערמים זה על זה ולא ניתן לקרוא:
  ;;   DIMATFIT 3 — כשאין מקום, הטקסט והחצים יוצאים החוצה
  ;;   DIMTMOVE 1 — טקסט שיצא מקבל קו מוביל, כדי שיהיה ברור לאיזו מידה
  ;;   DIMTOFL  1 — קו המידה נמשך בין קווי העזר גם כשהטקסט בחוץ
  (setvar "DIMATFIT" 3) (setvar "DIMTMOVE" 1) (setvar "DIMTOFL" 1)
  (vl-catch-all-apply 'setvar (list "DIMBLK" "_ARCHTICK")))

;;; ציור כל הנספח. p0 = פינה ימנית-תחתונה, scl = מכנה קנה המידה
(defun mg:drawall (p0 scl / x0 y0 th r gap hatch? maxw secy tw py miny)
  (mg:mklayers) (mg:style) (mg:setup scl)
  (setq th (* 0.25 scl))          ; טקסט 2.5 מ"מ בנייר
  (setq hatch? T  gap (* 1.2 scl))

  ;; שורת תוכניות — מנקודת הבסיס שמאלה
  (setq x0 (car p0) y0 (cadr p0) maxw 0.0)
  (foreach r *MMD-LIST*
    (setq tw (+ (nth 1 r) (nth 1 (nth 4 r)) (nth 3 (nth 4 r))))
    (setq x0 (- x0 tw (* 0.6 gap)))
    ;; mg:plan מחזירה את התחתית בפועל (סוף בלוק הנתונים) — שורת החתכים
    ;; תיפול מתחתיה במקום מרחק קבוע שמתנגש כשהדלת רחבה.
    (setq py (mg:plan r x0 (+ y0 (* 1.6 gap)) th hatch?))
    (setq miny (if miny (min miny py) py))
    (mg:text "TEXT" (list (+ x0 (/ (nth 1 r) 2.0))
                          (+ y0 (* 1.6 gap) (nth 2 r) (nth 0 (nth 4 r)) (* 0.35 gap)))
             (* th 1.3)
             (strcat "\U+05EA\U+05D5\U+05DB\U+05E0\U+05D9\U+05EA " (nth 0 r) " \U+05E7\U+05E0\"\U+05DE 1:" (rtos scl 2 0)) 1 0)
    (setq maxw (max maxw (+ (nth 2 r) (nth 0 (nth 4 r)) (nth 2 (nth 4 r)))))
    (setq x0 (- x0 (* 1.4 gap))))

  ;; שורת חתכים מתחת
  ;; החתכים מתחת לתחתית התוכניות, בתוספת מרווח למידות שמעל התקרה.
  (setq x0 (car p0) secy (- (if miny miny y0) (* 1.6 gap)))
  (foreach r *MMD-LIST*
    (setq tw (+ (nth 1 r) (nth 1 (nth 4 r)) (nth 3 (nth 4 r))))
    (setq x0 (- x0 tw (* 0.6 gap)))
    (mg:section r x0 (- secy (nth 3 r)) th hatch?)
    (setq x0 (- x0 (* 1.4 gap))))

  ;; הערות בלבד מימין לנקודת הבסיס.
  ;; אין טבלה מרכזת — לפי החלטת המשתמש 27.08.2026 הנתונים מופיעים על
  ;; כל ממ"ד בתוכנית שלו (mg:info). mg:table נשמרה בקוד למקרה שיידרש.
  (mg:notes (+ (car p0) (* 14.0 gap)) y0 th))

(defun c:MMDDRAW ( / *error* sv vals p0 scl)
  (setq sv (mg:sysvars) vals (mapcar 'getvar sv))
  (defun *error* (m)
    (mapcar '(lambda (n v) (vl-catch-all-apply 'setvar (list n v))) sv vals)
    (if (and m (not (wcmatch (strcase m) "*BREAK*,*CANCEL*,*QUIT*")))
      (princ (strcat "\nMMDDRAW: " m)))
    (princ))

  (if (null *MMD-LIST*) (mg:load))
  (if (null *MMD-LIST*)
    (progn (princ "\nאין מרחבים ברשימה — הפעל MMD קודם.") (exit)))

  (setq p0 (getpoint "\nנקודת בסיס לנספח (פינה ימנית-תחתונה): "))
  (if (null p0) (exit))
  (setq scl (getreal "\nקנה מידה 1:<50>: "))
  (if (null scl) (setq scl 50.0))

  (mg:drawall p0 scl)

  (mapcar '(lambda (n v) (vl-catch-all-apply 'setvar (list n v))) sv vals)
  (princ (strcat "\n=== הנספח נוצר: " (itoa (length *MMD-LIST*)) " מרחבים ==="))
  (princ))

;;; ==================================================================
;;;  MMDTEST — בדיקה עצמית, אפס קליקים
;;;  מצייר נספח הדגמה ומדפיס דוח תקינות דו-לשוני.
;;;  הדוח באנגלית בכוונה: אם העברית משובשת והאנגלית קריאה,
;;;  הבעיה היא בקידוד ולא בכלי.
;;; ==================================================================
(defun c:MMDTEST ( / *error* sv vals saved n0 n1 ok units fp r1
                     rL lpts c opts obb ew eh dirty clean ar)
  (setq sv (mg:sysvars) vals (mapcar 'getvar sv))
  (defun *error* (m)
    (mapcar '(lambda (n v) (vl-catch-all-apply 'setvar (list n v))) sv vals)
    (princ (strcat "\n[FAIL] MMDTEST: " (if m m "?")))
    (princ))

  (princ "\n")
  (princ "\n============================================================")
  (princ "\n  MIGUN SELF-TEST  /  בדיקה עצמית")
  (princ "\n============================================================")
  (princ (strcat "\n  AutoCAD    : " (getvar "ACADVER")))
  (princ (strcat "\n  Build      : " *MG-BUILD*
                 "   <-- must match migun.lsp.src / חייב להתאים למקור"))
  (princ (strcat "\n  Found at   : "
                 (if (setq fp (findfile "migun.lsp")) fp "(not on search path)")))
  (setq units (getvar "INSUNITS"))
  (princ (strcat "\n  INSUNITS   : " (itoa units) "  "
                 (cond ((= units 4) "= CENTIMETERS  <-- expected / כצפוי")
                       ((= units 5) "= MILLIMETERS  <-- see note below")
                       ((= units 6) "= METERS       <-- see note below")
                       ((= units 0) "= UNITLESS (probably fine / כנראה תקין)")
                       (T "= other"))))
  (princ (strcat "\n  Drawing    : " (getvar "DWGNAME")))

  ;; שמירת רשימה קיימת והחלפתה בנתוני הדגמה
  (setq saved *MMD-LIST*)
  ;; TEST-1 נושא עובי מילוי מפורש; TEST-2 בכוונה **בלי** השדה — כדי
  ;; שהטסט יריץ גם את מסלול הרשומה הישנה ויוודא שהיא עדיין נטענת.
  (setq *MMD-LIST* (list
    ;; (id L W H (tN tE tS tW) tCeil tFloor ops [fill])
    (list "TEST-1" 300.0 260.0 250.0 (list 25.0 25.0 20.0 25.0) 20.0 15.0
      (list (list "door" "S"  40.0  80.0 200.0   0.0 "A" "1")
            (list "win"  "N" 100.0 100.0 100.0 105.0 "A")
            (list "vent" "N" 240.0  20.0  20.0 190.0 "A"))
      8.0)
    (list "TEST-2" 340.0 280.0 250.0 (list 30.0 25.0 25.0 25.0) 20.0 15.0
      (list (list "door" "W"  60.0  80.0 200.0   0.0 "B" "1")
            (list "win"  "E" 120.0 100.0 100.0 105.0 "A")))))

  (setq n0 (if (entlast) 1 0))
  (princ "\n  Drawing demo annex at 0,0 ... / מצייר נספח הדגמה")
  (mg:drawall '(0.0 0.0 0.0) 50.0)

  ;; בדיקות
  (princ "\n------------------------------------------------------------")
  (setq ok T)
  (foreach nm '("WALL" "DOOR" "WINDOW" "VENT" "DIM" "TEXT" "TABLE" "SECTION")
    (if (tblsearch "LAYER" (strcat *MG-PREFIX* nm))
      (princ (strcat "\n  [ok]   layer " *MG-PREFIX* nm))
      (progn (setq ok nil)
             (princ (strcat "\n  [FAIL] layer " *MG-PREFIX* nm " missing")))))
  (if (tblsearch "STYLE" (strcat *MG-PREFIX* "TXT"))
    (princ (strcat "\n  [ok]   text style " *MG-PREFIX* "TXT (" *MG-FONT* ")"))
    (progn (setq ok nil) (princ "\n  [FAIL] text style missing")))

  ;; שטח ונפח — TEST-1 הוא 300x260x250 ס"מ ? 7.80 מ"ר ו-19.50 מ"ק
  (setq r1 (car *MMD-LIST*))
  (if (< (abs (- (mg:area r1) 7.8)) 0.005)
    (princ "\n  [ok]   area   7.80 m2")
    (progn (setq ok nil)
           (princ (strcat "\n  [FAIL] area = " (rtos (mg:area r1) 2 3)
                          " expected 7.800"))))
  (if (< (abs (- (mg:vol r1) 19.5)) 0.005)
    (princ "\n  [ok]   volume 19.50 m3")
    (progn (setq ok nil)
           (princ (strcat "\n  [FAIL] volume = " (rtos (mg:vol r1) 2 3)
                          " expected 19.500"))))
  ;; רשומה בלי שדה מילוי חייבת ליפול לברירת המחדל, לא ל-nil
  (if (equal (mg:fill (cadr *MMD-LIST*)) *MG-FILL* 0.001)
    (princ "\n  [ok]   legacy record falls back to default fill")
    (progn (setq ok nil) (princ "\n  [FAIL] legacy record fill lookup")))
  (if (equal (mg:fill r1) 8.0 0.001)
    (princ "\n  [ok]   explicit fill read from record")
    (progn (setq ok nil) (princ "\n  [FAIL] explicit fill lookup")))

  ;; ---- מנוע הפוליגון, על ממ"ד בצורת ר' ----
  ;; 400x300 ועוד 200x200 = 16.00 מ"ר, היקף 18.00 מ', נפח 40.00 מ"ק
  (setq lpts (list '(0.0 0.0) '(400.0 0.0) '(400.0 300.0)
                   '(200.0 300.0) '(200.0 500.0) '(0.0 500.0)))
  (setq rL (list "L-SHAPE" 400.0 500.0 250.0 '(25.0 25.0 25.0 25.0) 20.0 15.0
                 nil 7.0 lpts '(25.0 25.0 20.0 20.0 25.0 30.0)))
  (foreach c (list
      (list "polygon area   16.00 m2" (mg:area rL)  16.0)
      (list "polygon volume 40.00 m3" (mg:vol  rL)  40.0)
      (list "polygon perim  1800 cm"  (mg:perim rL) 1800.0))
    (if (equal (cadr c) (caddr c) 0.005)
      (princ (strcat "\n  [ok]   " (car c)))
      (progn (setq ok nil)
             (princ (strcat "\n  [FAIL] " (car c) " got "
                            (rtos (cadr c) 2 3))))))
  ;; כיוון: הפוליגון חייב לצאת נגד כיוון השעון גם אם הוזן הפוך
  (if (> (mg:sarea (car (mg:ccw (reverse lpts) nil))) 0.0)
    (princ "\n  [ok]   reversed polygon is re-oriented CCW")
    (progn (setq ok nil) (princ "\n  [FAIL] mg:ccw did not re-orient")))
  ;; מלבן ישן חייב להיקרא כפוליגון בן 4 צלעות עם אותו שטח
  (if (and (= 4 (length (car (mg:poly r1))))
           (equal (mg:area r1) 7.8 0.005))
    (princ "\n  [ok]   legacy rectangle reads as a 4-edge polygon")
    (progn (setq ok nil) (princ "\n  [FAIL] rectangle->polygon")))
  ;; פוליגון חיצוני: התיבה החיצונית חייבת להיות פנים + עובי משני הצדדים.
  ;; הציפייה נגזרת מהרשומה ולא נכתבת כמספר — כך היא לא מתיישנת אם
  ;; ה-fixture משתנה. (טעות שלי בגרסה הראשונה: כתבתי 310 בעוד שקיר
  ;; הדרום ב-TEST-1 הוא 20 ולא 25, כלומר 305. הבדיקה תפסה את זה.)
  (setq opts (mg:outer (car (mg:poly r1)) (cadr (mg:poly r1))))
  (setq obb (mg:bbox opts))
  (setq ew (+ (nth 1 r1) (nth 1 (nth 4 r1)) (nth 3 (nth 4 r1))))
  (setq eh (+ (nth 2 r1) (nth 0 (nth 4 r1)) (nth 2 (nth 4 r1))))
  (if (and (equal (- (caddr obb) (car obb)) ew 0.01)
           (equal (- (cadddr obb) (cadr obb)) eh 0.01))
    (princ (strcat "\n  [ok]   outer polygon offsets/miters ("
                   (rtos ew 2 0) " x " (rtos eh 2 0) ")"))
    (progn (setq ok nil)
           (princ (strcat "\n  [FAIL] outer bbox "
                          (rtos (- (caddr obb) (car obb)) 2 2) " x "
                          (rtos (- (cadddr obb) (cadr obb)) 2 2)
                          " expected " (rtos ew 2 2) " x " (rtos eh 2 2)))))
  ;; ---- נקודה בתוך פוליגון ----
  (if (and (mg:inpoly '(200.0 100.0) lpts)          ; בתוך הזרוע התחתונה
           (mg:inpoly '(100.0 400.0) lpts)          ; בתוך הזרוע השמאלית
           (not (mg:inpoly '(350.0 400.0) lpts))    ; בחלל שמחוץ ל-ר'
           (not (mg:inpoly '(500.0 100.0) lpts)))   ; מחוץ לגמרי
    (princ "\n  [ok]   point-in-polygon incl. the concave notch")
    (progn (setq ok nil) (princ "\n  [FAIL] mg:inpoly")))

  ;; ---- ניקוי קו פנים ----
  ;; אותה צורת ר', אבל "מלוכלכת" כמו שקו אדריכל מגיע מ-BOUNDARY:
  ;; קודקוד מיותר באמצע צלע ישרה, קפיצה של 2 ס"מ, ועוד קודקוד על קו.
  ;; אחרי הניקוי חייבות להישאר בדיוק 6 צלעות, ושטח זהה.
  (setq dirty (list '(0.0 0.0) '(200.0 0.0) '(400.0 0.0) '(400.0 300.0)
                    '(398.0 300.0) '(200.0 300.0) '(200.0 500.0)
                    '(0.0 500.0) '(0.0 250.0)))
  (setq clean (mg:simplify dirty 15.0 (/ (* 4.0 pi) 180.0)))
  (if (= (length clean) 6)
    (princ "\n  [ok]   simplify: 9 noisy vertices -> 6")
    (progn (setq ok nil)
           (princ (strcat "\n  [FAIL] simplify gave " (itoa (length clean))
                          " vertices, expected 6"))))
  ;; ניקוי משנה שטח במעט — זה בלתי נמנע. הדרישה: השינוי קטן מ-1%,
  ;; **ותמיד כלפי מטה**. שטח מוגן עודף מול הרשות המוסמכת מסוכן יותר
  ;; משטח חסר, ולכן זו לא רק שאלת דיוק אלא כיוון.
  (setq ar (abs (mg:sarea clean)))
  (if (and (<= ar 160000.0) (> ar (* 160000.0 0.99)))
    (princ (strcat "\n  [ok]   simplify errs low and under 1% ("
                   (rtos ar 2 0) " of 160000)"))
    (progn (setq ok nil)
           (princ (strcat "\n  [FAIL] area after simplify " (rtos ar 2 1)
                          " — must be <=160000 and within 1%"))))

  ;; ופוליגון קעור: בצורת ר' התיבה החיצונית מתרחבת בעובי הצלעות הקיצוניות
  (setq opts (mg:outer (car (mg:poly rL)) (cadr (mg:poly rL))))
  (if (= (length opts) 6)
    (princ "\n  [ok]   concave polygon keeps all 6 corners")
    (progn (setq ok nil)
           (princ (strcat "\n  [FAIL] concave outer has "
                          (itoa (length opts)) " corners, expected 6"))))

  ;; חזרה למצב הקודם
  (setq *MMD-LIST* saved)
  (mapcar '(lambda (n v) (vl-catch-all-apply 'setvar (list n v))) sv vals)

  (vl-catch-all-apply 'vl-cmdf (list "_.ZOOM" "_E"))

  (princ "\n------------------------------------------------------------")
  (if ok
    (progn
      (princ "\n  RESULT: PASS")
      (princ "\n  You should now SEE on screen:")
      (princ "\n    - 2 protected-space plans, hatched walls, door arc, window")
      (princ "\n    - 2 sections below them")
      (princ "\n    - a summary table + numbered notes on the right")
      (princ "\n  אם אתה רואה את כל אלה — הכלי עובד.")
      (princ "\n  Hebrew above garbled but English readable? tell me - encoding only.")
      (princ "\n  To erase the demo:  MMDWIPE"))
    (princ "\n  RESULT: FAIL - send me this whole text (F2 to copy)"))
  (princ "\n============================================================")
  (princ))

;;; ==================================================================
;;;  MMDWIPE — מחיקת כל מה שהכלי צייר (שכבות MIGUN-*)
;;; ==================================================================
(defun c:MMDWIPE ( / ss i n)
  (setq n 0)
  (foreach rec *MG-LAYERS*
    (if (setq ss (ssget "_X" (list (cons 8 (strcat *MG-PREFIX* (car rec))))))
      (repeat (setq i (sslength ss))
        (entdel (ssname ss (setq i (1- i))))
        (setq n (1+ n)))))
  (princ (strcat "\nנמחקו " (itoa n) " ישויות / erased " (itoa n) " entities."))
  (princ))

;;; ---------- עזרי ניהול ----------
(defun c:MMDLIST ( / r)
  (if (null *MMD-LIST*) (mg:load))
  (princ (strcat "\n" (itoa (length *MMD-LIST*)) " מרחבים:"))
  (foreach r *MMD-LIST*
    (princ (strcat "\n  " (nth 0 r) "  " (rtos (nth 1 r) 2 0) "x" (rtos (nth 2 r) 2 0)
                   "  (" (rtos (/ (* (nth 1 r) (nth 2 r)) 10000.0) 2 2) " מ\"ר)  "
                   (itoa (length (nth 7 r))) " פתחים")))
  (princ))

(defun c:MMDDEL ( / id)
  (if (null *MMD-LIST*) (mg:load))
  (setq id (getstring T "\nשם המרחב למחיקה: "))
  (setq *MMD-LIST* (vl-remove-if '(lambda (r) (= (car r) id)) *MMD-LIST*))
  (mg:save)
  (princ (strcat "\nנותרו " (itoa (length *MMD-LIST*)) " מרחבים."))
  (princ))

(defun c:MMDCLR ()
  (setq *MMD-LIST* '())
  (mg:save)
  (princ "\nהרשימה נוקתה.")
  (princ))

(princ (strcat "\n=== MIGUN.LSP נטען   (build " *MG-BUILD* ") ==="))
(princ "\n  >>> חדש כאן? הקלד  MMDTEST  לבדיקה עצמית ללא קליקים <<<")
(princ "\n  MMDCUT — קליק אחד בתוך המרחב: גוזר אותו מהתוכנית אל הנספח")
(princ "\n  MMD — סימון מרחב מוגן | MMDDRAW — יצירת נספח | MMDDETAILS — פרטי פתחים")
(princ "\n  MMDLIB — ספריית בלוקים | MMDTEST — בדיקה | MMDWIPE — מחיקת מה שצוייר")
(princ "\n  MMDLIST | MMDDEL | MMDCLR")
(princ)
